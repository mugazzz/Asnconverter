CDRCCN {iso(1) member-body(2) bsi(826) disc(0) ericsson(1249)
mobileDomain (0) charging (5) cDRCCN (1) asn1Module (0)
version4 (2)}
DEFINITIONS IMPLICIT TAGS ::=
BEGIN
EXPORTS ChargingDataOutputRecord;
--IMPORTS SDPCreditControlRecord FROM CreditControlRecord {iso(1) member-body(2) bsi(826) disc(0) ericsson(1249) mobileDomain (0) charging (5) creditControlDataTypes (1) asn1Module (0) version4 (3)};
ChargingDataOutputRecord ::= CHOICE {
	   sCFPDPRecord                 [0]  SCFPDPRecord,
	   sCFSMSPSMORecord             [1]  SCFSMSMORecord,
	   sCFSMSCSMORecord             [2]  SCFSMSMORecord,
	   diameterCreditControlRecord  [3] DiameterCreditControlRecord,
	   fBCRatingRecord              [4]  FBCRatingRecord,
	   rTCCreditControlRecord       [5]  RTCCreditControlRecord,
	   onlineCreditControlRecord    [6]  OnlineCreditControlRecord
	   
}

SCFPDPRecord ::= SEQUENCE {
	chargingID                  [0] ChargingID,
	accessPointName             [2] AccessPointName OPTIONAL,
	recordSequenceNumber        [3] RecordSequenceNumber,
	nodeID                      [4] NodeID,
	localSequenceNumber         [5] LocalSequenceNumber,
	lastPartialOutput           [6] BOOLEAN,
	trafficCase                 [7] TrafficCase OPTIONAL,
	subscriberNumber            [8] AddressString OPTIONAL,
	serviceClass                [9] ServiceClass OPTIONAL,
	accountValueBefore          [10]	MoneyAmount OPTIONAL,
	accountValueAfter           [11]	MoneyAmount OPTIONAL,
	finalCharge                 [12]	MoneyAmount OPTIONAL,
	chargedDuration             [13]	ChargedDuration OPTIONAL,
	cdrReason                   [14]	CdrReason,
	teleServiceCode             [15]	TeleServiceCode OPTIONAL,
	startOfChargingOfContext    [16]	TimeStamp OPTIONAL,
	familyAndFriendsIndicator   [17]	FamilyAndFriendsIndicator
	                                                  OPTIONAL,
	numberOfSDPInterrogations   [18]	NumberOfSDPInterrogations,
	dataVolume                  [19]	DataVolume OPTIONAL,
	currencyType                [20]	CurrencyType OPTIONAL,
	callingPartyNumber          [21]	AddressString OPTIONAL,
	originatingLocationInfo     [22]	AddressString OPTIONAL,
	accountNumber               [23]	AddressString OPTIONAL,
	terminatingLocationInfo     [24]	AddressString OPTIONAL,
	calledPartyNumber           [25]	AddressString OPTIONAL,
	accumulatorValueInfo        [26]	SEQUENCE (SIZE(1..5)) OF 
                                   AccumulatorValueInfo OPTIONAL,
	dedicatedAccountInfo        [27]	SEQUENCE (SIZE(1..5)) OF
                                   DedicatedAccountInfo OPTIONAL,
	accountGroupID              [28]	AccountGroupID OPTIONAL,
	serviceOfferings            [29]	ServiceOfferings OPTIONAL,
	communityDataInfo           [30]	SEQUENCE OF CommunityDataInfo
                                                      OPTIONAL,
	triggerTime                 [31]	TimeStamp OPTIONAL,
 -- ID:03565
	 cellID                     [32] CellID OPTIONAL,
	 locationAreaID             [33] LocationAreaID OPTIONAL,
 -- end ID:03565
	categorizationInformation   [34] CategorizationInformation             
                                    OPTIONAL, 	
	ratedDurations              [35] RatedDurations OPTIONAL
	

}

SCFSMSMORecord ::= SEQUENCE {
	servedIMSI                  [0] IMSI,
	servedMSISDN                [1] AddressString,
	serviceCenter               [2] AddressString,
	nodeID                      [3] NodeID,
	localSequenceNumber         [4] LocalSequenceNumber,
	trafficCase                 [5] TrafficCase OPTIONAL,
	serviceClass                [6] ServiceClass OPTIONAL,
	accountValueBefore          [7] MoneyAmount OPTIONAL,
	accountValueAfter           [8] MoneyAmount OPTIONAL,
	finalCharge                 [9] MoneyAmount OPTIONAL,
	cdrReason                   [10]	CdrReason,
	teleServiceCode             [11]	TeleServiceCode OPTIONAL,
	startOfChargingOfEvent      [12]	TimeStamp OPTIONAL,
	familyAndFriendsIndicator   [13]	FamilyAndFriendsIndicator
	                                                OPTIONAL,
	numberOfSDPInterrogations   [14]	NumberOfSDPInterrogations,
	currencyType                [15]	CurrencyType OPTIONAL,
	originatingLocationInfo     [16]	AddressString OPTIONAL,
	accountNumber               [17]	AddressString OPTIONAL,
	destinationNumber           [18]	AddressString,
	accumulatorValueInfo        [19]	SEQUENCE (SIZE(1..5)) OF
                                   AccumulatorValueInfo OPTIONAL,
	dedicatedAccountInfo        [20]	SEQUENCE (SIZE(1..5)) OF
                                   DedicatedAccountInfo OPTIONAL,
	eventTimeStamp              [21]	TimeStamp,
	networkID                   [22]	NetworkID OPTIONAL,
	smsReferenceNumber          [23]	CallReferenceNumber OPTIONAL,
	mscAddress                  [24]	AddressString OPTIONAL,
	sgsn-Number                 [25]	AddressString OPTIONAL,
	accountGroupID              [26]	AccountGroupID OPTIONAL,
	serviceOfferings            [27]	ServiceOfferings OPTIONAL,
	communityDataInfo           [28]	SEQUENCE OF CommunityDataInfo
                                                      OPTIONAL,
	calledPartyNumber           [29]	AddressString OPTIONAL,

 -- ID:03565
	 cellID                     [30] CellID OPTIONAL,
	 locationAreaID             [31] LocationAreaID OPTIONAL,
 -- end ID:03565
	categorizationInformation   [32] CategorizationInformation             
                                    OPTIONAL, 	
	ratedDurations              [33] RatedDurations OPTIONAL

}

DiameterCreditControlRecord ::= SEQUENCE {
	cdrReason                    [0]	CdrReason,
	nodeID                       [1]	NodeID,
	recordSequenceNumber         [2]	RecordSequenceNumber,
	lastPartialOutput            [3]	BOOLEAN,
	trafficCase                  [4]	TrafficCase OPTIONAL,
	teleServiceCode              [5]	TeleServiceCode OPTIONAL,
	subscriberID                 [6]	AddressString OPTIONAL,
	callingPartyNumber           [7]	AddressString OPTIONAL,
	calledPartyNumber            [8]	AddressString OPTIONAL,
	triggerTime                  [9]	TimeStamp OPTIONAL,
	chargedDuration              [10]	ChargedDuration OPTIONAL,
	dataVolume                   [11]	DataVolume OPTIONAL,
	numberOfEvents               [12]	NumberOfEvents OPTIONAL,
	finalCharge                  [13]	MoneyAmount OPTIONAL,
	accountValueBefore           [14]	MoneyAmount OPTIONAL,
	accountValueAfter            [15]	MoneyAmount OPTIONAL,
	sessionID                    [16]	SessionID,
	userName                     [17]	UserName OPTIONAL,
	numberOfSDPInterrogations    [18]	NumberOfSDPInterrogations,
	originRealm                  [19]	OriginRealm OPTIONAL,
	originHost                   [20]	OriginHost OPTIONAL,
	serviceClass                 [21]	ServiceClass OPTIONAL,
	accountNumber                [22]	AddressString OPTIONAL,
	localSequenceNumber          [23]	LocalSequenceNumber,
	familyAndFriendsIndicator    [24]	FamilyAndFriendsIndicator
	                                                  OPTIONAL,
	currencyType                 [25]	CurrencyType OPTIONAL,
	accumulatorValueInfo         [26]	SEQUENCE (SIZE(1..5)) OF
                                      AccumulatorValueInfo OPTIONAL,
	dedicatedAccountInfo         [27]	SEQUENCE (SIZE(1..5)) OF
                                      DedicatedAccountInfo OPTIONAL,
	serviceProviderID            [28]	ServiceProviderID OPTIONAL,
	extInt1                      [29]	ExtInt OPTIONAL,
	extInt2                      [30]	ExtInt OPTIONAL,
	extInt3                      [31]	ExtInt OPTIONAL,
	extInt4                      [32]	ExtInt OPTIONAL,
	extText                      [33]	ExtText OPTIONAL,
	gprsQoS                      [34]	GPRSQoS OPTIONAL,
	redirectingPartyNumber       [35]	AddressString OPTIONAL,
	originatingLocationInfo      [36]	AddressString OPTIONAL,
	terminatingLocationInfo      [37]	AddressString OPTIONAL,
	networkID                    [38]	NetworkID OPTIONAL,
	subscriptionType             [39]	SubscriptionType OPTIONAL,
	smsDeliveryStatus            [40]	SmsDeliveryStatus OPTIONAL,
	calledPartyNumber2           [41]	AddressString OPTIONAL,
	calledPartyNumber3           [42]	AddressString OPTIONAL,
	radiusSessionID              [43]	RadiusSessionID OPTIONAL,
	multiSessionID               [44]	MultiSessionID OPTIONAL,
	originalSubscriptionIDData   [45]	SubscriptionIDData OPTIONAL,
	originalSubscriptionIDType   [46]	SubscriptionIDType OPTIONAL,
	accountingCorrelationID      [47]	AccountingCorrelationID
	                                                 OPTIONAL,
	abnormalTerminationReason    [48]	AbnormalTerminationReason
	                                                  OPTIONAL,
	accountGroupID               [49]	AccountGroupID OPTIONAL,
	serviceOfferings             [50]	ServiceOfferings OPTIONAL,
	communityDataInfo            [51]	SEQUENCE OF CommunityDataInfo
                                                      OPTIONAL,
 -- ID:02587 
	usedAmountLastInterval       [52]	MoneyAmount OPTIONAL,
	deductedAmountLastInterval   [53]	MoneyAmount OPTIONAL,
 -- end ID:02587
	categorizationInformation    [54] CategorizationInformation
                                                 OPTIONAL,
	ratedDurations               [55] RatedDurations OPTIONAL
 
}

FBCRatingRecord ::= SEQUENCE {
	serviceClassInfo             [0]	SEQUENCE OF ServiceClassInfo,
	chargingID                   [2]	SEQUENCE OF ChargingID,
	timeStamp                    [3]	TimeStamp,
	volumeULAccumulatedTotal     [4]	DataVolume,
	volumeDLAccumulatedTotal     [5]	DataVolume,
	subscriberGroup              [6]	SubscriberGroup,
	nodeID                       [7]	NodeID,
	localSequenceNumber          [8]	LocalSequenceNumber,
	servedIMSI                   [9]	IMSI OPTIONAL,
	servedMSISDN                 [10]	AddressString OPTIONAL,
	userName                     [11]	UserName OPTIONAL,
	recoveryData                 [12] RecoveryRecord OPTIONAL,
	serviceClassExtendedInfo     [13] SEQUENCE OF 
                                   ServiceClassExtendedInfo
                                   OPTIONAL,
	ratingRequested              [14] BOOLEAN OPTIONAL,
	ratingSuccessful             [15] BOOLEAN OPTIONAL,
	startOfUsageInfo             [16] SEQUENCE OF StartOfUsageInfo
                                   OPTIONAL
	
}

RTCCreditControlRecord ::= SEQUENCE {
	cdrReason                    [0]	CdrReason,
	nodeID                       [1]	NodeID,
	recordSequenceNumber         [2]	RecordSequenceNumber,
	lastPartialOutput            [3]	BOOLEAN,
	trafficCase                  [4]	TrafficCase OPTIONAL,
	teleServiceCode              [5]	TeleServiceCode OPTIONAL,
	subscriberID                 [6]	AddressString OPTIONAL,
	callingPartyNumber           [7]	AddressString OPTIONAL, 
	calledPartyNumber            [8]	AddressString OPTIONAL,
	triggerTime                  [9]	TimeStamp OPTIONAL,
	chargedDuration              [10] ChargedDuration OPTIONAL,
	servedIMSI                   [11] IMSI OPTIONAL,
	numberOfEvents               [12] NumberOfEvents OPTIONAL,
	finalCharge                  [13] MoneyAmount OPTIONAL,
	accountValueBefore           [14] MoneyAmount OPTIONAL,
	accountValueAfter            [15] MoneyAmount OPTIONAL,
	accountingCorrelationID      [16] AccountingCorrelationID,
	numberOfSDPInterrogations    [17] NumberOfSDPInterrogations,
	serviceClass                 [18] ServiceClass OPTIONAL,
	accountNumber                [19] AddressString OPTIONAL,
	localSequenceNumber          [20] LocalSequenceNumber,
	familyAndFriendsIndicator    [21] FamilyAndFriendsIndicator
                                     OPTIONAL,
	currencyType                 [22] CurrencyType OPTIONAL,
	accumulatorValueInfo         [23] SEQUENCE (SIZE(1..5)) OF
                                     AccumulatorValueInfo OPTIONAL,
	dedicatedAccountInfo         [24] SEQUENCE (SIZE(1..5)) OF
                                     DedicatedAccountInfo OPTIONAL,
	redirectingPartyNumber       [25] AddressString OPTIONAL,
	originatingLocationInfo      [26] AddressString OPTIONAL,
	terminatingLocationInfo      [27] AddressString OPTIONAL,
	networkID                    [28] NetworkID OPTIONAL,
	subscriptionType             [29] SubscriptionType OPTIONAL,
	calledPartyNumber2           [30] AddressString OPTIONAL,
	calledPartyNumber3           [31] AddressString OPTIONAL,
	accountGroupID               [32] AccountGroupID OPTIONAL,
	serviceOfferings             [33] ServiceOfferings OPTIONAL,
	communityDataInfo            [34] SEQUENCE OF CommunityDataInfo
                                                      OPTIONAL,
	serviceCenter                [35] AddressString OPTIONAL,
	startOfCharging              [36] TimeStamp OPTIONAL,
	callSetUpResultCode          [37] CallSetUpResultCode OPTIONAL,
	usedUnchargedDuration        [38] UsedUnchargedDuration OPTIONAL,
	usedUnchargedEvent           [39] UsedUnchargedEvent OPTIONAL,
	categorizationInformation    [40] CategorizationInformation
                                                 OPTIONAL,
	ratedDurations               [41] RatedDurations OPTIONAL
 
}

OnlineCreditControlRecord ::= SEQUENCE {
 resultCode                  [0] Unsigned32,
 resultCodeExtension         [1] Unsigned32 OPTIONAL,
 triggerTime                 [2] TimeStamp,
 nodeName                    [3] UTF8String (SIZE(1..255)),
 serviceContextID            [4] UTF8String,
 chargingContextID           [5] ChargingContext,
 serviceSessionID            [6] UTF8String,
 recordIdentificationNumber  [7] RecordIdentificationNumber,
 partialSequenceNumber       [8] INTEGER OPTIONAL,
 lastPartialOutput           [9] BOOLEAN OPTIONAL,
 servedSubscriptionID        [10] SEQUENCE OF SubscriptionID
                                                    OPTIONAL,
 correlationID               [11] EXPLICIT CorrelationID OPTIONAL,
 servingElement              [12] EXPLICIT ServingElement OPTIONAL,
 creditControlRecords        [13] SEQUENCE OF SDPCreditControlRecord OPTIONAL,
                                                      
 usedUnchargedServiceUnits   [14] UsedServiceUnits OPTIONAL
 
}

AbnormalTerminationReason ::= ENUMERATED {
	serviceElementTermination    (0),
	connectionToUserBroken       (1)
}

AccessPointName ::= OCTET STRING (SIZE(1..100))

AccountGroupID ::= INTEGER (0..2147483647)
-- 0                undefined
-- 1 - 2147483647   accountGroupID

AccountingCorrelationID ::= UTF8String (SIZE (1..255))

AcctMultiSessionID ::= OCTET STRING (SIZE (1..255))

AccumulatorID ::= INTEGER (1..2147483647)

AccumulatorValue ::= INTEGER (-2147483648..2147483647)

AccumulatorValueInfo ::= SEQUENCE {
        accumulatorID            [0] AccumulatorID OPTIONAL,
        accumulatorValue         [1] AccumulatorValue OPTIONAL,
        accumulatorDeltaValue    [2] AccumulatorValue OPTIONAL
        
}

AddressString ::= OCTET STRING (SIZE (1..20))
--AddressString ::= UTF8String (SIZE (1..255))

CallReferenceNumber ::= OCTET STRING (SIZE (1..8))

CallSetUpResultCode ::= ENUMERATED {
 successful-ReleasedByService                    (0),
 successful-DisconnectByCallingParty             (1),
 successful-DisconnectByCalledParty              (2),
 successful-OngoingTollFree                      (3),
 non-Successful-CalledPartyRouteSelectFailure    (4),
 non-Successful-CalledPartyBusy                  (5),
 non-Successful-CalledPartyNotReachable          (6),
 non-Successful-CalledPartyNoAnswer              (7),
 non-Successful-CallingPartyAbandon              (8),
 non-Successful-OtherReason                      (14),
 callForwardingHasBeenInvoked-ChargingCancelled  (15)
}

CampaignIdentifier ::= INTEGER (1..99999999)

CategoryValue ::= INTEGER (0..999)

CategorizationInformation ::= SEQUENCE {
 categoryType1 [1] CategoryValue OPTIONAL,
 categoryType2 [2] CategoryValue OPTIONAL,
 categoryType3 [3] CategoryValue OPTIONAL,
 categoryType4 [4] CategoryValue OPTIONAL
 
}

CdrReason ::= ENUMERATED {
 serviceClassRequested                             (0),
 firstInterrogationUnsuccessful                    (1),
 invokeIntermediateInterrogationFinalReportUnsucc  (2),
 internalError                                     (3),
 subscriberTemporaryBlocked                        (4),
 partialDeduction                                  (5)
 
}

CellID ::= OCTET STRING (SIZE(7))

ChargingContext ::= UTF8String (SIZE (1..255))

ChargedDuration ::= OCTET STRING (SIZE(1..4))

ChargingID ::= OCTET STRING (SIZE(1..4))

CommunityDataInfo ::= SEQUENCE {
 selectedCommunityIndicator         [0] SelectedCommunityIndicator
                                         OPTIONAL,
 communityIDCharged                 [1] SEQUENCE (SIZE(1..3))
                                         OF CommunityID OPTIONAL,
 communityIDNonCharged              [2] SEQUENCE (SIZE(1..3))
                                         OF CommunityID OPTIONAL,
 communityDataNonChargedNotAvailable[3] BOOLEAN OPTIONAL
 
}

CommunityID ::= INTEGER (1..9999999)

CorrelationID ::= CHOICE {
   callReference                 [0] CallReferenceNumber,
   chargingID                    [1] ChargingID,
   accountingCorrelationID       [2] AccountingCorrelationID,
   dccCorrelationId              [3] DccCorrelationID
   
}

CurrencyType ::= ENUMERATED {
	localCurrency  (0),
	eURO           (1)
}

DAID ::= INTEGER (1..255)

DataVolume ::= OCTET STRING (SIZE(1..4))

DccCorrelationID ::=  SEQUENCE {
   acctMultiSessionID      [0] AcctMultiSessionID OPTIONAL,
   ccCorrelationId         [1] OCTET STRING OPTIONAL,
   sessionId               [2] UTF8String OPTIONAL,
   ccRequestNumber         [3] Unsigned32 OPTIONAL
   
}

DedicatedAccountAccDuration ::= INTEGER (0..2147483647)

DedicatedAccountInfo ::= SEQUENCE {
   identity                 [1] DAID OPTIONAL,
   valueBefore              [2] MoneyAmount OPTIONAL,
   valueAfter               [3] MoneyAmount OPTIONAL,
   campaignIdentifier       [4] CampaignIdentifier OPTIONAL,
   accumulatedDuration      [5] DedicatedAccountAccDuration
                                                  OPTIONAL
   
}

ExtInt ::= INTEGER (0..65535)

ExtText ::= OCTET STRING (SIZE (1..29))

FamilyAndFriendsIndicator ::= INTEGER (1..65535)

GPRSQoS ::= INTEGER (0..32767)

IMSI ::= OCTET STRING (SIZE (3..8))

Integer32 ::= INTEGER (-2147483648..2147483647)

Integer64 ::= INTEGER (-9223372036854775808..9223372036854775807)

IPBinaryAddress ::= CHOICE {
	iPBinV4Address      [0] OCTET STRING (SIZE(4)),
	iPBinV6Address      [1] OCTET STRING (SIZE(16))
}

LocationAreaID ::= OCTET STRING (SIZE(5))

LocalSequenceNumber ::= OCTET STRING (SIZE(1..4))

MonetaryUnits ::= SEQUENCE 
{
  amount       [0] Integer64,
  decimals     [1] Integer32,
  currency     [2] Unsigned32
}

--MoneyAmount ::= OCTET STRING (SIZE (1..17))
MoneyAmount ::= INTEGER (0..65535)

MultiSessionID ::= OCTET STRING (SIZE (1..255))

NetworkID ::= INTEGER (0..65534)

NodeID ::= OCTET STRING (SIZE (1..20))

NumberOfEvents	::= INTEGER (0..65535)

NumberOfSDPInterrogations ::= INTEGER (1..65535)

OriginHost ::= OCTET STRING (SIZE (1..255))

OriginInfo ::= SEQUENCE {
	originRealm                 [0] OriginRealm OPTIONAL,
	originHost                  [1] OriginHost OPTIONAL
	
}

OriginRealm ::= OCTET STRING (SIZE (1..255))

RadiusSessionID ::= OCTET STRING (SIZE (1..127))

RatedDurations ::= SEQUENCE {
 debitDuration  [0] ChargedDuration OPTIONAL,
 creditDuration [1] ChargedDuration OPTIONAL,
 freeDuration   [2] ChargedDuration OPTIONAL
 
}

RecordIdentificationNumber ::= OCTET STRING (SIZE(1..4))

RecordSequenceNumber ::= OCTET STRING (SIZE(1..4))

RecoveryRecord ::= SEQUENCE {
	ccnTimeStamp                 [0] TimeStamp,
	accumulatorModificationDate  [1] TimeStamp,
	recoveryState                [2] RecoveryState,
	globalDeltaVolumeUL          [3] DataVolume OPTIONAL,
	globalDeltaVolumeDL          [4] DataVolume OPTIONAL,
	serviceClassDeltaValueList   [5] SEQUENCE OF 
                                  RecoveryServiceClassInfo
                                  OPTIONAL
	
}

RecoveryServiceClassInfo ::= SEQUENCE {
	serviceClass                 [0] ServiceClass,
	deltaTime                    [1] DataVolume OPTIONAL,
	deltaVolumeUL                [2] DataVolume OPTIONAL,
	deltaVolumeDL                [3] DataVolume OPTIONAL
	
}

RecoveryState ::= ENUMERATED {
	normal                       (1),
	provisioningRecovery         (2),
	cdrRecovery                  (3)
}

SelectedCommunityIndicator ::= INTEGER (0..9999999)

ServiceClass ::= INTEGER (0..65535)

ServiceClassExtendedInfo ::= SEQUENCE {
	serviceClass                 [0] ServiceClass,
	timeAccumulated              [1] DataVolume
	
}

ServiceOfferings ::= INTEGER (0..2147483647)
-- 0                undefined
-- 1 - 2147483647   serviceOfferings

ServiceProviderID ::= INTEGER (0..65535)

ServiceClassInfo ::= SEQUENCE {
	serviceClass        [0] ServiceClass,
	volumeULAccumulated [1] DataVolume,
	volumeDLAccumulated [2] DataVolume
}

ServingElement ::= CHOICE {
	originInfo                 [0] OriginInfo,
	mSCAddress                 [1] AddressString
	
}

SessionID ::= OCTET STRING (SIZE (1..255))

SmsDeliveryStatus ::= ENUMERATED {
	delivered        (1),
	expired          (2)
}

StartOfUsageInfo ::= SEQUENCE {
	serviceClass        [0] ServiceClass,
	startOfUsage        [1] TimeStamp
}

SubscriberGroup ::= OCTET STRING (SIZE(1..4))

SubscriptionID    ::= SEQUENCE {
   subscriptionIDType     [0] SubscriptionIDType,
   subscriptionIDValue    [1] SubscriptionIDData
}

SubscriptionIDData ::= UTF8String (SIZE (1..255))

SubscriptionIDType ::= ENUMERATED {
	endUserE164      (0),
	endUserIMSI      (1),
	endUserSIPURI    (2),
	endUserNAI       (3),
	endUserPrivate   (4)
	
}

SubscriptionType ::= INTEGER (0..127)

TariffChangeUsage ::= ENUMERATED
{
	before            (0),
	after             (1),
	indeterminate     (2)
}

TeleServiceCode ::= ENUMERATED {
	voice             (0),
	fax               (1),
	data              (2),
	unknown           (3),
	sMS               (4),
	gPRS              (5),
	content           (6),
	videoTelephony    (7),
	videoConference   (8),
	extensionTSC1     (65526),
	extensionTSC2     (65527),
	extensionTSC3     (65528),
	extensionTSC4     (65529),
	extensionTSC5     (65530),
	extensionTSC6     (65531),
	extensionTSC7     (65532),
	extensionTSC8     (65533),
	extensionTSC9     (65534),
	extensionTSC10    (65535)
}

TimeStamp ::= OCTET STRING (SIZE(9))

TrafficCase ::= ENUMERATED {
	originatingInsideHPLMN        (0),
	forwardedInsideHPLMN          (1),
	terminatingInsideHPLMN        (2),
	originatingOutsideHPLMNCAPv1  (3),
	forwardedOutsideHPLMNCAPv1    (4),
	terminatingOutsideHPLMN       (5),
	roamingCallBackOutsideHPLMN   (6),
	originatingOutsideHPLMNCAPv2  (7),
	forwardedOutsideHPLMNCAPv2    (8),
	terminatingOutsideHPLMNCAPv2  (9),
	originatingOutsideHPLMNCAPv3  (10),
	forwardedOutsideHPLMNCAPv3    (11),
	terminatingOutsideHPLMNCAPv3  (12),
	originatingServiceCharging    (20),
	terminatingServiceCharging    (21)
}

Unsigned32 ::= INTEGER (0..4294967295) 

Unsigned64 ::= INTEGER (0..18446744073709551615)

UsedServiceUnit ::= SEQUENCE {   
 tariffChangeUsage           [0] TariffChangeUsage OPTIONAL,   
 timeUnit                    [1] Unsigned32 OPTIONAL,   
 moneyUnit                   [2] MonetaryUnits OPTIONAL,   
 totalOctetsUnit             [3] Unsigned64 OPTIONAL,   
 uplinkOctetsUnit            [4] Unsigned64 OPTIONAL,
 downlinkOctetsUnit          [5] Unsigned64 OPTIONAL,   
 serviceSpecificUnit         [6] Unsigned64 OPTIONAL   
  
}

UsedServiceUnits ::= SEQUENCE (SIZE (1..3)) OF UsedServiceUnit

UsedUnchargedDuration ::= OCTET STRING (SIZE(1..4))

UsedUnchargedEvent ::= OCTET STRING (SIZE(1..4))

UserName ::= OCTET STRING (SIZE (1..255))

SDPCreditControlRecord ::= CHOICE
{
creditControlRecord [0] CreditControlRecord
}

CreditControlRecord ::= SEQUENCE
{
serviceIdentifier [1] Unsigned32,
usedServiceUnits [2] UsedServiceUnits OPTIONAL,
eventTime [3] TimeStamp,
triggerTime [4] TimeStamp,
serviceScenario [5] ServiceScenario,
serviceExtension [6] ServiceExtension
OPTIONAL,
roamingPosition [7] RoamingPosition OPTIONAL,
tariffInfo [8] SEQUENCE OF
SelectionTreeParameter OPTIONAL,
cCAccountData [9] CCAccountData,
chargingContextSpecific [10] SEQUENCE OF
ContextParameter OPTIONAL,
treeDefinedFields [11] SEQUENCE OF
TreeDefinedField OPTIONAL,
bonusAdjustment [12] BonusAdjustment OPTIONAL,
serviceSetupResult [13] ServiceSetupResult OPTIONAL,
terminationCause [14] TerminationCause OPTIONAL,
ratedUnits [15] RatedUnits OPTIONAL,
-- PC
individualPriceFactorHistory [16] SEQUENCE OF
IndividualPriceFactorHistory OPTIONAL
-- end PC

}
--------------------------------------------------------------
--
-- CREDIT CONTROL DATA TYPES
--
--------------------------------------------------------------
AccountFlags ::= IA5String (SIZE (8))
Accumulator ::= SEQUENCE
{
accumulatorID [0] AccumulatorID,
accumulatorBefore [1] Integer32 OPTIONAL,
accumulatorChange [2] Integer32,
accumulatorAfter [3] Integer32,
accumulatorBeforeSession [4] Integer32 OPTIONAL

}
Accumulators ::= SEQUENCE (SIZE (1..255)) OF Accumulator
BonusAdjustment ::= SEQUENCE
{
accountValueBefore [0] MonetaryUnits OPTIONAL,
accountValueAfter [1] MonetaryUnits OPTIONAL,
bonusAmount [2] MonetaryUnits OPTIONAL,
accumulators [3] Accumulators OPTIONAL,
dedicatedAccounts [4] DedicatedAccounts OPTIONAL,
lifeCycleInformation [5] LifeCycleInformation OPTIONAL

}
CCAccountData ::= SEQUENCE
{
servedAccount [0] AddressString,
serviceClassID [1] ServiceClassID,
accountGroupID [2] AccountGroupID,
accountValueBefore [3] MonetaryUnits OPTIONAL,
accountValueAfter [4] MonetaryUnits OPTIONAL,
communityInformation [5] CommunityInformation OPTIONAL,
accumulators [6] Accumulators OPTIONAL,
dedicatedAccounts [7] DedicatedAccounts OPTIONAL,
familyAndFriendsID [8] FamilyAndFriendsID OPTIONAL,
familyAndFriendsNo [9] AddressString OPTIONAL,
serviceOfferings [10] Unsigned32,
accumulatedCost [11] MonetaryUnits OPTIONAL,
accountValueUsed [12] MonetaryUnits OPTIONAL,
accountValueDeducted [13] MonetaryUnits

}
CommunityIDs ::= SEQUENCE
{
communityID1 [0] CommunityID OPTIONAL,
communityID2 [1] CommunityID OPTIONAL,
communityID3 [2] CommunityID OPTIONAL

}
CommunityInformation ::= SEQUENCE
{
selectedCommunityID [0] CommunityID OPTIONAL,
servedCommunityIDs [1] CommunityIDs OPTIONAL,
nonServedCommunityIDs [2] CommunityIDs OPTIONAL,
nonServedCommunityIDNA [3] BOOLEAN OPTIONAL,
nonServedCommunityNo [4] AddressString OPTIONAL

}
ContextParameter ::= SEQUENCE
{
parameterID [0] Integer64,
parameterValue [1] ContextParameterValueType
}
ContextParameterValueType ::= CHOICE
{
boolean [0] BOOLEAN,
unsigned32 [3] Unsigned32,
unsigned64 [4] Unsigned64,
addressString [5] AddressString,
octetString [6] OCTET STRING,
string [7] UTF8String,
time [8] Time,
partyInformation [9] PartyInformation

}
Date ::= IA5String (SIZE (8))
DedicatedAccount ::= SEQUENCE
{
dedicatedAccountID [0] DedicatedAccountID,
dedicatedAccountValueBefore [1] MonetaryUnits OPTIONAL,
dedicatedAccountValueAfter [2] MonetaryUnits OPTIONAL,
dedicatedAccountChange [3] MonetaryUnits OPTIONAL,
dedicatedAccountCampaignID [4] DedicatedAccountCampaignID
OPTIONAL,
accountExpiryDateBefore [5] Date OPTIONAL,
accountExpiryDateAfter [6] Date OPTIONAL

}
DedicatedAccountID ::= INTEGER (1..2147483647)
DedicatedAccountCampaignID ::= INTEGER (0..99999999)
DedicatedAccounts ::= SEQUENCE (SIZE (1..255)) OF DedicatedAccount
FamilyAndFriendsID ::= INTEGER (1..65535)
IndividualPriceFactorHistory ::= SEQUENCE
{
inidividualPriceFactor [0] Percent,
units [1] ServiceUnits

}
LifeCycleInformation ::= SEQUENCE
{
supervisionExpDateBefore [0] Date OPTIONAL,
supervisionExpDateAfter [1] Date OPTIONAL,
creditClearancePeriodBefore [2] Period OPTIONAL,
creditClearancePeriodAfter [3] Period OPTIONAL,
servFeeExpDateBefore [4] Date OPTIONAL,
servFeeExpDateAfter [5] Date OPTIONAL,
serviceRemovalPeriodBefore [6] Period OPTIONAL,
serviceRemovalPeriodAfter [7] Period OPTIONAL,
accountFlagsBefore [8] AccountFlags OPTIONAL,
accountFlagsAfter [9] AccountFlags OPTIONAL

}
PartyInformation ::= CHOICE
{
msisdn [0] AddressString,
imsi [1] AddressString,
sipUri [2] UTF8String,
nai [3] UTF8String

}
Percent ::= IA5String (SIZE (1..10))
Period ::= INTEGER (0..1023)
RatedUnits ::= SEQUENCE
{
debitUnits [0] RatedUnitsValues OPTIONAL,
creditUnits [1] RatedUnitsValues OPTIONAL,
freeUnits [2] RatedUnitsValues OPTIONAL

}
RatedUnitsValues ::= SEQUENCE
{
ratedTimeUnits [0] Unsigned32 OPTIONAL,
ratedTotalOctetsUnits [1] Unsigned64 OPTIONAL,
ratedUplinkOctetsUnits [2] Unsigned64 OPTIONAL,
ratedDownlinkOctetsUnits [3] Unsigned64 OPTIONAL,
ratedServiceSpecificUnits [4] Unsigned64 OPTIONAL

}
RoamingPosition ::= ENUMERATED
{
insideHPLMN(0),
outsideHPLMN(1)

}
SelectionTreeParameter ::= SEQUENCE
{
selectionTreeID [0] UTF8String,
selectionTreeVersion [1] UTF8String,
selectionTreeType [2] SelectionTreeType

}
SelectionTreeType ::= ENUMERATED
{
rating(0),
bonus(1),
selection(2),
dedicatedAccount(3),
communityCharging(4),
numberNormalization(5),
ussdTextMessage(6),
accountManagement(7),
preAnalysis(8)

}
ServiceClassID ::= INTEGER (0..9999)
ServiceExtension ::= ENUMERATED
{
ussdCallback(0),
capV1Roaming(1)

}
ServiceSetupResult ::= ENUMERATED
{
successfulReleasedByService(0),
successfulDisconnectedByCallingParty(1),
successfulDisconnectByCalledParty(2),
successfulTollfree(3),
nonSuccessfulCalledPartyRouteSelectFailure(4),
nonSuccessfulCalledPartyBusy(5),
nonSuccessfulCalledPartyNotReachable(6),
nonSuccessfulCalledPartyNoAnswer(7),
nonSuccessfulCallingPartyAbandon(8),
nonSuccessfulOtherReason(14),
callForwardingChargingCancelled(15)

}
ServiceScenario ::= ENUMERATED
{
mobileOriginating(0),
mobileForwarding(1),
mobileTerminating(2)

}
ServiceUnits ::= SEQUENCE
{
timeUnit [1] Unsigned32 OPTIONAL,
moneyUnit [2] MonetaryUnits OPTIONAL,
totalOctetsUnit [3] Unsigned64 OPTIONAL,
uplinkOctetsUnit [4] Unsigned64 OPTIONAL,
downlinkOctetsUnit [5] Unsigned64 OPTIONAL,
serviceSpecificUnit [6] Unsigned64 OPTIONAL

}
TerminationCause ::= ENUMERATED
{
diameterLogout(1),
diameterServiceNotProvided(2),
diameterBadAnswer(3),
diameterAdministrative(4),
diameterLinkBroken(5),
diameterAuthExpired(6),
diameterUserMoved(7),
diameterSessionTimeout(8)
}
Time ::= SEQUENCE
{
sec [0] Integer32,
tz [1] INTEGER(-128..127)
}
TreeDefinedField ::= SEQUENCE
{
parameterID [0] UTF8String,
parameterValue [1] TreeDefinedFieldType
}
TreeDefinedFieldType ::= CHOICE
{
boolean [0] BOOLEAN,
integer64 [2] Integer64,
string [7] UTF8String

} 
END
