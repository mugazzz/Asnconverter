-- ASN.1 Formal Description

CDRCCN DEFINITIONS IMPLICIT TAGS ::=

BEGIN

EXPORTS SDPCreditControlRecord, UsedServiceUnits;

ChargingDataOutputRecord ::= CHOICE {
	   sCFPDPRecord                 [0]  SCFPDPRecord,
	   sCFSMSPSMORecord             [1]  SCFSMSMORecord,
	   sCFSMSCSMORecord             [2]  SCFSMSMORecord,
	   diameterCreditControlRecord  [3]  DiameterCreditControlRecord,
	   fBCRatingRecord              [4]  FBCRatingRecord,
	   rTCCreditControlRecord       [5]  RTCCreditControlRecord,
	   onlineCreditControlRecord    [6]  OnlineCreditControlRecord
}

SCFPDPRecord ::= SEQUENCE {
	chargingID                  [0] ChargingID,
	ggsnAddressUsed             [1] GSNAddress,
	accessPointName             [2] AccessPointName OPTIONAL,
	recordSequenceNumber        [3] RecordSequenceNumber,
	nodeID                      [4] NodeID,
	localSequenceNumber         [5] LocalSequenceNumber,
	lastPartialOutput           [6] BOOLEAN,
	trafficCase                 [7] TrafficCase OPTIONAL,
	subscriberNumber            [8] AddressString OPTIONAL,
	serviceClass                [9] ServiceClass OPTIONAL,
	accountValueBefore          [10]	MoneyAmount OPTIONAL,
	accountValueAfter           [11]	MoneyAmount OPTIONAL,
	finalCharge                 [12]	MoneyAmount OPTIONAL,
	chargedDuration             [13]	ChargedDuration OPTIONAL,
	cdrReason                   [14]	CdrReason,
	teleServiceCode             [15]	TeleServiceCode OPTIONAL,
	startOfChargingOfContext    [16]	TimeStamp OPTIONAL,
	familyAndFriendsIndicator   [17]	FamilyAndFriendsIndicator OPTIONAL,
	numberOfSDPInterrogations   [18]	NumberOfSDPInterrogations,
	dataVolume                  [19]	DataVolume OPTIONAL,
	currencyType                [20]	CurrencyType OPTIONAL,
	callingPartyNumber          [21]	AddressString OPTIONAL,
	originatingLocationInfo     [22]	AddressString OPTIONAL,
	accountNumber               [23]	AddressString OPTIONAL,
	terminatingLocationInfo     [24]	AddressString OPTIONAL,
	calledPartyNumber           [25]	AddressString OPTIONAL,
	accumulatorValueInfo        [26]	SEQUENCE (SIZE(1..5)) OF AccumulatorValueInfo OPTIONAL,
	dedicatedAccountInfo        [27]	SEQUENCE (SIZE(1..5)) OF DedicatedAccountInfo OPTIONAL,
	accountGroupID              [28]	AccountGroupID OPTIONAL,
	serviceOfferings            [29]	ServiceOfferings OPTIONAL,
	communityDataInfo           [30]	SEQUENCE OF CommunityDataInfo OPTIONAL,
	triggerTime                 [31]	TimeStamp OPTIONAL,
 -- ID:03565
	 cellID                     [32] CellID OPTIONAL,
	 locationAreaID             [33] LocationAreaID OPTIONAL,
 -- end ID:03565
	categorizationInformation   [34] CategorizationInformation OPTIONAL,
	ratedDurations              [35] RatedDurations OPTIONAL
}

SCFSMSMORecord ::= SEQUENCE {
	servedIMSI                  [0] IMSI,
	servedMSISDN                [1] AddressString,
	serviceCenter               [2] AddressString,
	nodeID                      [3] NodeID,
	localSequenceNumber         [4] LocalSequenceNumber,
	trafficCase                 [5] TrafficCase OPTIONAL,
	serviceClass                [6] ServiceClass OPTIONAL,
	accountValueBefore          [7] MoneyAmount OPTIONAL,
	accountValueAfter           [8] MoneyAmount OPTIONAL,
	finalCharge                 [9] MoneyAmount OPTIONAL,
	cdrReason                   [10]	CdrReason,
	teleServiceCode             [11]	TeleServiceCode OPTIONAL,
	startOfChargingOfEvent      [12]	TimeStamp OPTIONAL,
	familyAndFriendsIndicator   [13]	FamilyAndFriendsIndicator OPTIONAL,
	numberOfSDPInterrogations   [14]	NumberOfSDPInterrogations,
	currencyType                [15]	CurrencyType OPTIONAL,
	originatingLocationInfo     [16]	AddressString OPTIONAL,
	accountNumber               [17]	AddressString OPTIONAL,
	destinationNumber           [18]	AddressString,
	accumulatorValueInfo        [19]	SEQUENCE (SIZE(1..5)) OF AccumulatorValueInfo OPTIONAL,
	dedicatedAccountInfo        [20]	SEQUENCE (SIZE(1..5)) OF DedicatedAccountInfo OPTIONAL,
	eventTimeStamp              [21]	TimeStamp,
	networkID                   [22]	NetworkID OPTIONAL,
	smsReferenceNumber          [23]	CallReferenceNumber OPTIONAL,
	mscAddress                  [24]	AddressString OPTIONAL,
	sgsn-Number                 [25]	AddressString OPTIONAL,
	accountGroupID              [26]	AccountGroupID OPTIONAL,
	serviceOfferings            [27]	ServiceOfferings OPTIONAL,
	communityDataInfo           [28]	SEQUENCE OF CommunityDataInfo OPTIONAL,
	calledPartyNumber           [29]	AddressString OPTIONAL,
 -- ID:03565
	 cellID                     [30] CellID OPTIONAL,
	 locationAreaID             [31] LocationAreaID OPTIONAL,
 -- end ID:03565
	categorizationInformation   [32] CategorizationInformation OPTIONAL,
	ratedDurations              [33] RatedDurations OPTIONAL
}

DiameterCreditControlRecord ::= SEQUENCE {
	cdrReason                    [0]	CdrReason,
	nodeID                       [1]	NodeID,
	recordSequenceNumber         [2]	RecordSequenceNumber,
	lastPartialOutput            [3]	BOOLEAN,
	trafficCase                  [4]	TrafficCase OPTIONAL,
	teleServiceCode              [5]	TeleServiceCode OPTIONAL,
	subscriberID                 [6]	AddressString OPTIONAL,
	callingPartyNumber           [7]	AddressString OPTIONAL,
	calledPartyNumber            [8]	AddressString OPTIONAL,
	triggerTime                  [9]	TimeStamp OPTIONAL,
	chargedDuration              [10]	ChargedDuration OPTIONAL,
	dataVolume                   [11]	DataVolume OPTIONAL,
	numberOfEvents               [12]	NumberOfEvents OPTIONAL,
	finalCharge                  [13]	MoneyAmount OPTIONAL,
	accountValueBefore           [14]	MoneyAmount OPTIONAL,
	accountValueAfter            [15]	MoneyAmount OPTIONAL,
	sessionID                    [16]	SessionID,
	userName                     [17]	UserName OPTIONAL,
	numberOfSDPInterrogations    [18]	NumberOfSDPInterrogations,
	originRealm                  [19]	OriginRealm OPTIONAL,
	originHost                   [20]	OriginHost OPTIONAL,
	serviceClass                 [21]	ServiceClass OPTIONAL,
	accountNumber                [22]	AddressString OPTIONAL,
	localSequenceNumber          [23]	LocalSequenceNumber,
	familyAndFriendsIndicator    [24]	FamilyAndFriendsIndicator OPTIONAL,
	currencyType                 [25]	CurrencyType OPTIONAL,
	accumulatorValueInfo         [26]	SEQUENCE (SIZE(1..5)) OF AccumulatorValueInfo OPTIONAL,
	dedicatedAccountInfo         [27]	SEQUENCE (SIZE(1..5)) OF DedicatedAccountInfo OPTIONAL,
	serviceProviderID            [28]	ServiceProviderID OPTIONAL,
	extInt1                      [29]	ExtInt OPTIONAL,
	extInt2                      [30]	ExtInt OPTIONAL,
	extInt3                      [31]	ExtInt OPTIONAL,
	extInt4                      [32]	ExtInt OPTIONAL,
	extText                      [33]	ExtText OPTIONAL,
	gprsQoS                      [34]	GPRSQoS OPTIONAL,
	redirectingPartyNumber       [35]	AddressString OPTIONAL,
	originatingLocationInfo      [36]	AddressString OPTIONAL,
	terminatingLocationInfo      [37]	AddressString OPTIONAL,
	networkID                    [38]	NetworkID OPTIONAL,
	subscriptionType             [39]	SubscriptionType OPTIONAL,
	smsDeliveryStatus            [40]	SmsDeliveryStatus OPTIONAL,
	calledPartyNumber2           [41]	AddressString OPTIONAL,
	calledPartyNumber3           [42]	AddressString OPTIONAL,
	radiusSessionID              [43]	RadiusSessionID OPTIONAL,
	multiSessionID               [44]	MultiSessionID OPTIONAL,
	originalSubscriptionIDData   [45]	SubscriptionIDData OPTIONAL,
	originalSubscriptionIDType   [46]	SubscriptionIDType OPTIONAL,
	accountingCorrelationID      [47]	AccountingCorrelationID OPTIONAL,
	abnormalTerminationReason    [48]	AbnormalTerminationReason OPTIONAL,
	accountGroupID               [49]	AccountGroupID OPTIONAL,
	serviceOfferings             [50]	ServiceOfferings OPTIONAL,
	communityDataInfo            [51]	SEQUENCE OF CommunityDataInfo OPTIONAL,
 -- ID:02587 
	usedAmountLastInterval       [52]	MoneyAmount OPTIONAL,
	deductedAmountLastInterval   [53]	MoneyAmount OPTIONAL,
 -- end ID:02587
	categorizationInformation    [54] CategorizationInformation OPTIONAL,
	ratedDurations               [55] RatedDurations OPTIONAL
}

FBCRatingRecord ::= SEQUENCE {
	serviceClassInfo             [0]	SEQUENCE OF ServiceClassInfo,
	ggsnAddressUsed              [1]	GSNAddress,
	chargingID                   [2]	SEQUENCE OF ChargingID,
	timeStamp                    [3]	TimeStamp,
	volumeULAccumulatedTotal     [4]	DataVolume,
	volumeDLAccumulatedTotal     [5]	DataVolume,
	subscriberGroup              [6]	SubscriberGroup,
	nodeID                       [7]	NodeID,
	localSequenceNumber          [8]	LocalSequenceNumber,
	servedIMSI                   [9]	IMSI OPTIONAL,
	servedMSISDN                 [10]	AddressString OPTIONAL,
	userName                     [11]	UserName OPTIONAL,
	recoveryData                 [12] RecoveryRecord OPTIONAL,
	serviceClassExtendedInfo     [13] SEQUENCE OF ServiceClassExtendedInfo OPTIONAL,
	ratingRequested              [14] BOOLEAN OPTIONAL,
	ratingSuccessful             [15] BOOLEAN OPTIONAL,
	startOfUsageInfo             [16] SEQUENCE OF StartOfUsageInfo OPTIONAL
}

RTCCreditControlRecord ::= SEQUENCE {
	cdrReason                    [0]	CdrReason,
	nodeID                       [1]	NodeID,
	recordSequenceNumber         [2]	RecordSequenceNumber,
	lastPartialOutput            [3]	BOOLEAN,
	trafficCase                  [4]	TrafficCase OPTIONAL,
	teleServiceCode              [5]	TeleServiceCode OPTIONAL,
	subscriberID                 [6]	AddressString OPTIONAL,
	callingPartyNumber           [7]	AddressString OPTIONAL,
	calledPartyNumber            [8]	AddressString OPTIONAL,
	triggerTime                  [9]	TimeStamp OPTIONAL,
	chargedDuration              [10] ChargedDuration OPTIONAL,
	servedIMSI                   [11] IMSI OPTIONAL,
	numberOfEvents               [12] NumberOfEvents OPTIONAL,
	finalCharge                  [13] MoneyAmount OPTIONAL,
	accountValueBefore           [14] MoneyAmount OPTIONAL,
	accountValueAfter            [15] MoneyAmount OPTIONAL,
	accountingCorrelationID      [16] AccountingCorrelationID,
	numberOfSDPInterrogations    [17] NumberOfSDPInterrogations,
	serviceClass                 [18] ServiceClass OPTIONAL,
	accountNumber                [19] AddressString OPTIONAL,
	localSequenceNumber          [20] LocalSequenceNumber,
	familyAndFriendsIndicator    [21] FamilyAndFriendsIndicator OPTIONAL,
	currencyType                 [22] CurrencyType OPTIONAL,
	accumulatorValueInfo         [23] SEQUENCE (SIZE(1..5)) OF AccumulatorValueInfo OPTIONAL,
	dedicatedAccountInfo         [24] SEQUENCE (SIZE(1..5)) OF DedicatedAccountInfo OPTIONAL,
	redirectingPartyNumber       [25] AddressString OPTIONAL,
	originatingLocationInfo      [26] AddressString OPTIONAL,
	terminatingLocationInfo      [27] AddressString OPTIONAL,
	networkID                    [28] NetworkID OPTIONAL,
	subscriptionType             [29] SubscriptionType OPTIONAL,
	calledPartyNumber2           [30] AddressString OPTIONAL,
	calledPartyNumber3           [31] AddressString OPTIONAL,
	accountGroupID               [32] AccountGroupID OPTIONAL,
	serviceOfferings             [33] ServiceOfferings OPTIONAL,
	communityDataInfo            [34] SEQUENCE OF CommunityDataInfo OPTIONAL,
	serviceCenter                [35] AddressString OPTIONAL,
	startOfCharging              [36] TimeStamp OPTIONAL,
	callSetUpResultCode          [37] CallSetUpResultCode OPTIONAL,
	usedUnchargedDuration        [38] UsedUnchargedDuration OPTIONAL,
	usedUnchargedEvent           [39] UsedUnchargedEvent OPTIONAL,
	categorizationInformation    [40] CategorizationInformation OPTIONAL,
	ratedDurations               [41] RatedDurations OPTIONAL
}

OnlineCreditControlRecord ::= SEQUENCE {
 resultCode                      [0] Unsigned32,
 resultCodeExtension             [1] Unsigned32 OPTIONAL,
 triggerTime                     [2] TimeStamp,
 nodeName                        [3] UTF8String (SIZE(1..255)),
 serviceContextID                [4] UTF8String,
 chargingContextID               [5] ChargingContext,
 serviceSessionID                [6] UTF8String,
 recordIdentificationNumber      [7] RecordIdentificationNumber,
 partialSequenceNumber           [8] INTEGER OPTIONAL,
 lastPartialOutput               [9] BOOLEAN OPTIONAL,
 servedSubscriptionID            [10] SEQUENCE OF SubscriptionID OPTIONAL,
 correlationID                   [11] CorrelationID OPTIONAL,
 servingElement                  [12] ServingElement OPTIONAL,
 creditControlRecords            [13] SEQUENCE OF SDPCreditControlRecord OPTIONAL,
 usedUnchargedServiceUnits       [14] UsedServiceUnits OPTIONAL,
 -- PC 07959, PC 12441
 originalCalledPartyNumber       [15] AddressString OPTIONAL,
 -- PC 07959, PC 12441 end
 -- PC
 chargedDuration                 [16] UsedServiceUnits OPTIONAL,
 usedStartPulses                 [17] OCTET STRING (SIZE(1..4)) OPTIONAL,
 -- PC end
 -- PC 08940
 nonServedSubscriptionID         [18] UTF8String OPTIONAL,
 -- PC 08940 end
 authorizedQoS                   [19] SEQUENCE OF AuthorizedQoS OPTIONAL,
 -- PC 09687
 firstCallInfo                   [20] AddressString OPTIONAL,
 -- PC 09687 end
 --PC:08842
 chargingSuppressionAtForwarding [21] ChargingSuppressionAtForwarding OPTIONAL,
 --PC:08842 end
 --PC:10210/PC:11890
 iMEI                            [22] IMEI OPTIONAL,
 -- PC:11890 end
 trunkInformation                [23] TrunkInformation OPTIONAL,
 -- PC:10210 end
 -- PC:10064 
 authorizedChargingRules         [24] SEQUENCE OF AuthorizedChargingRules OPTIONAL,
 -- PC:10064 end
 iMSChargingIdentifier          [25] IMSChargingIdentifier OPTIONAL,
 --PC:09785
 outgoingSessionId              [26] OutgoingSessionId OPTIONAL,
 -- PC:09785 end
 userSessionID                  [27] UserSessionID OPTIONAL,
 causeCode                      [28] CauseCode OPTIONAL,
 creditControlFailureHandling   [29] CreditControlFailureHandling OPTIONAL,
--PC:11040
 accessPointName                [30] AccessPointName OPTIONAL,
 dataVolume                     [31] DataVolume OPTIONAL,
 -- PC:11040 end
--PC:11376
receivedshortcodeNumber         [32] UTF8String OPTIONAL,
 -- PC:11376 end
relatedICIDs                    [33] SEQUENCE OF RelatedICID  OPTIONAL, 
-- PC:11460
redirectedPartyNumber           [34] AddressString OPTIONAL,
-- PC:11460 end
-- PC:11836
origServedSubscriptionID        [35] SEQUENCE OF SubscriptionID OPTIONAL,
-- PC:11836 end
-- PC:12422
callAttemptElapsedTimeValue     [36] CallAttemptElapsedTimeValue OPTIONAL,
locationAreaCode                [37] LocationAreaCode OPTIONAL,
mCC                             [38] MCC OPTIONAL,
mNC                             [39] MNC OPTIONAL,
releaseCauseCode                [40] ReleaseCauseCode OPTIONAL,
-- PC:12422 end
-- PC:12854
incomingAccessCapv4             [41] BOOLEAN OPTIONAL,
-- PC:12854 end
-- PC:12444
serviceScenario                 [42] ServiceScenario OPTIONAL,
roamingPosition                 [43] RoamingPosition OPTIONAL,
serviceExtension                [44] ServiceExtension OPTIONAL,
-- PC:12444 end
-- PC:11816
supplementaryService            [45] SEQUENCE OF SupplementaryServices OPTIONAL,
-- PC:11816 end
-- PC:13379
sdpRealm                        [46] OCTET STRING (SIZE (1..255)) OPTIONAL,
-- PC:13379 end
...
}

AbnormalTerminationReason ::= ENUMERATED {
	serviceElementTermination    (0),
	connectionToUserBroken       (1)
}

AccessPointName ::= OCTET STRING (SIZE(1..100))

AccountGroupID ::= INTEGER (0..2147483647)
-- 0                undefined
-- 1 - 2147483647   accountGroupID

AccountingCorrelationID ::= UTF8String (SIZE (1..255))

AcctMultiSessionID ::= OCTET STRING (SIZE (1..255))

AccumulatorID ::= INTEGER (1..2147483647)

AccumulatorValue ::= INTEGER (-2147483648..2147483647)

AccumulatorValueInfo ::= SEQUENCE {
        accumulatorID            [0] AccumulatorID OPTIONAL,
        accumulatorValue         [1] AccumulatorValue OPTIONAL,
        accumulatorDeltaValue    [2] AccumulatorValue OPTIONAL
}

AddressString ::= OCTET STRING (SIZE (1..20))

-- PC:11816
AssociatedPartyAddress ::= UTF8String
-- PC:11816 end

-- PC:10064
AuthorizedChargingRules ::= SEQUENCE {
  triggerTime                      [0] TimeStamp,
  activatedChargingRuleName        [1] SEQUENCE OF ChargingRuleName OPTIONAL,
  deactivatedChargingRuleName      [2] SEQUENCE OF ChargingRuleName OPTIONAL,
  activatedChargingRuleBaseName    [3] SEQUENCE OF ChargingRuleBaseName OPTIONAL,
  deactivatedChargingRuleBaseName  [4] SEQUENCE OF ChargingRuleBaseName OPTIONAL,
	...
}
-- PC:10064 end

AuthorizedQoS ::= SEQUENCE {
  triggerTime                  [0] TimeStamp,
  qoSClassIdentifier           [1] QoSClassIdentifier OPTIONAL,
  maxRequestedBandwidthUL      [2] Unsigned32 OPTIONAL,
  maxRequestedBandwidthDL      [3] Unsigned32 OPTIONAL,
  priorityLevel                [4] PriorityLevel OPTIONAL,
  preEmptionCapability         [5] BOOLEAN OPTIONAL,
  preEmptionVulnerability      [6] BOOLEAN OPTIONAL,
	...
}
-- PC:12422
CallAttemptElapsedTimeValue ::= INTEGER (0..255)
-- PC:12422 end

CallReferenceNumber ::= OCTET STRING (SIZE (1..8))

CallSetUpResultCode ::= ENUMERATED {
 successful-ReleasedByService                    (0),
 successful-DisconnectByCallingParty             (1),
 successful-DisconnectByCalledParty              (2),
 successful-OngoingTollFree                      (3),
 non-Successful-CalledPartyRouteSelectFailure    (4),
 non-Successful-CalledPartyBusy                  (5),
 non-Successful-CalledPartyNotReachable          (6),
 non-Successful-CalledPartyNoAnswer              (7),
 non-Successful-CallingPartyAbandon              (8),
 non-Successful-OtherReason                      (14),
 callForwardingHasBeenInvoked-ChargingCancelled  (15)
}

CampaignIdentifier ::= INTEGER (1..99999999)

CategoryValue ::= INTEGER (0..999)

CategorizationInformation ::= SEQUENCE {
 categoryType1 [1] CategoryValue OPTIONAL,
 categoryType2 [2] CategoryValue OPTIONAL,
 categoryType3 [3] CategoryValue OPTIONAL,
 categoryType4 [4] CategoryValue OPTIONAL
}

CauseCode ::= Integer32

CdrReason ::= ENUMERATED {
 serviceClassRequested                             (0),
 firstInterrogationUnsuccessful                    (1),
 invokeIntermediateInterrogationFinalReportUnsucc  (2),
 internalError                                     (3),
 subscriberTemporaryBlocked                        (4),
 partialDeduction                                  (5)
}

CellID ::= OCTET STRING (SIZE(7))

-- PC:11816
ChangeTime ::= TimeStamp
-- PC:11816 end

ChargingContext ::= UTF8String (SIZE (1..255))

ChargedDuration ::= OCTET STRING (SIZE(1..4))

ChargingID ::= OCTET STRING (SIZE(1..4))

-- PC:10064
ChargingRuleBaseName ::= UTF8String (SIZE (1..255))
ChargingRuleName ::= OCTET STRING (SIZE (1..255))
  -- PC:10064 end

-- PC:08842
ChargingSuppressionAtForwarding ::= ENUMERATED {
 notSuppressChargingAtForwarding (0),
 suppressChargingAtForwarding    (1)
}
-- PC:08842 end


CommunityDataInfo ::= SEQUENCE {
 selectedCommunityIndicator          [0] SelectedCommunityIndicator OPTIONAL,
 communityIDCharged                  [1] SEQUENCE (SIZE(1..3)) OF CommunityID OPTIONAL,
 communityIDNonCharged               [2] SEQUENCE (SIZE(1..3)) OF CommunityID OPTIONAL,
 communityDataNonChargedNotAvailable [3] BOOLEAN OPTIONAL
}

CommunityID ::= INTEGER (1..9999999)

CorrelationID ::= CHOICE {
   callReference                 [0] CallReferenceNumber,
   chargingID                    [1] ChargingID,
   accountingCorrelationID       [2] AccountingCorrelationID,
   dccCorrelationId              [3] DccCorrelationID
}

CreditControlFailureHandling ::= ENUMERATED {
  terminate (0),
  continue  (1)
}

-- PC:11816
CUGInformation ::= OCTET STRING
-- PC:11816 end

CurrencyType ::= ENUMERATED {
	localCurrency  (0),
	eURO           (1)
}

DAID ::= INTEGER (1..255)

DataVolume ::= OCTET STRING (SIZE(1..4))

DccCorrelationID ::=  SEQUENCE {
   acctMultiSessionID      [0] AcctMultiSessionID OPTIONAL,
   ccCorrelationId         [1] OCTET STRING OPTIONAL,
   sessionId               [2] UTF8String OPTIONAL,
   ccRequestNumber         [3] Unsigned32 OPTIONAL
}

DedicatedAccountAccDuration ::= INTEGER (0..2147483647)

DedicatedAccountInfo ::= SEQUENCE {
   identity                 [1] DAID OPTIONAL,
   valueBefore              [2] MoneyAmount OPTIONAL,
   valueAfter               [3] MoneyAmount OPTIONAL,
   campaignIdentifier       [4] CampaignIdentifier OPTIONAL,
   accumulatedDuration      [5] DedicatedAccountAccDuration OPTIONAL
}

ExtInt ::= INTEGER (0..65535)

ExtText ::= OCTET STRING (SIZE (1..29))

FamilyAndFriendsIndicator ::= INTEGER (1..65535)

GPRSQoS ::= INTEGER (0..32767)

GSNAddress ::= IPBinaryAddress

IndividualPriceFactor ::= INTEGER (0..999)

IndividualPriceFactorHistory ::=  SEQUENCE {
   individualPriceFactor1            [0] IndividualPriceFactor OPTIONAL,
   individualPriceFactor2            [1] IndividualPriceFactor OPTIONAL,
   individualPriceFactor1Units       [2] Units OPTIONAL,
   ...
}

-- PC:10210/PC:11890
IMEI ::= OCTET STRING (SIZE (8))
-- PC:10210/PC:11890 end

IMSChargingIdentifier ::= UTF8String (SIZE (1..255))

IMSI ::= OCTET STRING (SIZE (3..8))

Integer32 ::= INTEGER (-2147483648..2147483647)

Integer64 ::= INTEGER (-9223372036854775808..9223372036854775807)

IPBinaryAddress ::= CHOICE {
	iPBinV4Address      [0] OCTET STRING (SIZE(4)),
	iPBinV6Address      [1] OCTET STRING (SIZE(16))
}

-- PC:12422
LocationAreaCode ::= OCTET STRING (SIZE(2))
-- PC:12422 end

LocationAreaID ::= OCTET STRING (SIZE(5))

LocalSequenceNumber ::= OCTET STRING (SIZE(1..4))

-- PC:12422
MCC ::= OCTET STRING (SIZE(2))

MNC ::= OCTET STRING (SIZE(2))
-- PC:12422 end

MonetaryUnits ::= SEQUENCE 
{
  amount       [0] Integer64,
  decimals     [1] Integer32,
  currency     [2] Unsigned32
}

MoneyAmount ::= OCTET STRING (SIZE (1..17))

MultiSessionID ::= OCTET STRING (SIZE (1..255))

NetworkID ::= INTEGER (0..65534)

NodeID ::= OCTET STRING (SIZE (1..20))

-- PC:11816
NumberOfDiversions ::= Unsigned32
-- PC:11816 end

NumberOfEvents	::= INTEGER (0..65535)

-- PC:11816
NumberOfParticipants ::= Unsigned32
-- PC:11816 end

NumberOfSDPInterrogations ::= INTEGER (1..65535)

OriginHost ::= OCTET STRING (SIZE (1..255))

OriginInfo ::= SEQUENCE {
	originRealm                 [0] OriginRealm OPTIONAL,
	originHost                  [1] OriginHost OPTIONAL
}

OriginRealm ::= OCTET STRING (SIZE (1..255))

-- PC:09785
OutgoingSessionId ::= UTF8String (SIZE (1..255))
-- PC:09785 end

-- PC:11816
ParticipantActionType ::= ENUMERATED {
createConf	   (0),
joinConf	      (1),
inviteIntoConf	(2),
quitConf	      (3),
...
}
-- PC:11816 end

PriorityLevel ::= INTEGER (1..15)

QoSClassIdentifier ::= INTEGER (0..255)

RadiusSessionID ::= OCTET STRING (SIZE (1..127))

RatedDurations ::= SEQUENCE {
 debitDuration  [0] ChargedDuration OPTIONAL,
 creditDuration [1] ChargedDuration OPTIONAL,
 freeDuration   [2] ChargedDuration OPTIONAL
}

RecordIdentificationNumber ::= OCTET STRING (SIZE(1..4))

RecordSequenceNumber ::= OCTET STRING (SIZE(1..4))

RecoveryRecord ::= SEQUENCE {
	ccnTimeStamp                 [0] TimeStamp,
	accumulatorModificationDate  [1] TimeStamp,
	recoveryState                [2] RecoveryState,
	globalDeltaVolumeUL          [3] DataVolume OPTIONAL,
	globalDeltaVolumeDL          [4] DataVolume OPTIONAL,
	serviceClassDeltaValueList   [5] SEQUENCE OF RecoveryServiceClassInfo OPTIONAL
}

RecoveryServiceClassInfo ::= SEQUENCE {
	serviceClass                 [0] ServiceClass,
	deltaTime                    [1] DataVolume OPTIONAL,
	deltaVolumeUL                [2] DataVolume OPTIONAL,
	deltaVolumeDL                [3] DataVolume OPTIONAL
}

RecoveryState ::= ENUMERATED {
	normal                       (1),
	provisioningRecovery         (2),
	cdrRecovery                  (3)
}

RelatedICID ::= UTF8String (SIZE (1..255))

-- PC:12422
ReleaseCauseCode ::= OCTET STRING (SIZE(2))
-- PC:12422 end


-- PC:12444
RoamingPosition ::= ENUMERATED {
 insideHPLMN                 (0),
 outsideHPLMN                (1),
 ...
}

-- PC:12444 end

SelectedCommunityIndicator ::= INTEGER (0..9999999)

ServiceClass ::= INTEGER (0..65535)

ServiceClassExtendedInfo ::= SEQUENCE {
	serviceClass                 [0] ServiceClass,
	timeAccumulated              [1] DataVolume
}

-- PC:11816
ServiceID ::= UTF8String
-- PC:11816 end

-- PC:11816
ServiceMode ::= Unsigned32
-- PC:11816 end

ServiceOfferings ::= INTEGER (0..2147483647)
-- 0                undefined
-- 1 - 2147483647   serviceOfferings

ServiceProviderID ::= INTEGER (0..65535)

ServiceClassInfo ::= SEQUENCE {
	serviceClass        [0] ServiceClass,
	volumeULAccumulated [1] DataVolume,
	volumeDLAccumulated [2] DataVolume
}

-- PC:12444
ServiceScenario ::= ENUMERATED {
 mobileOriginating        (0),
 mobileForwarding         (1),
 mobileTerminating        (2),
 ...
}
-- PC:12444 end

-- PC:11816
ServiceType ::= Unsigned32
-- PC:11816 end

ServingElement ::= CHOICE {
	originInfo                 [0] OriginInfo,
	mSCAddress                 [1] AddressString,
	ggsnAddress                [2] GSNAddress,
	sgsnAddress                [3] GSNAddress
}

SessionID ::= OCTET STRING (SIZE (1..255))

SmsDeliveryStatus ::= ENUMERATED {
	delivered        (1),
	expired          (2)
}

StartOfUsageInfo ::= SEQUENCE {
	serviceClass        [0] ServiceClass,
	startOfUsage        [1] TimeStamp
}

SubscriberGroup ::= OCTET STRING (SIZE(1..4))

SubscriptionID    ::= SEQUENCE {
   subscriptionIDType     [0] SubscriptionIDType,
   subscriptionIDValue    [1] SubscriptionIDData
}

SubscriptionIDData ::= UTF8String (SIZE (1..255))

SubscriptionIDType ::= ENUMERATED {
	endUserE164      (0),
	endUserIMSI      (1),
	endUserSIPURI    (2),
	endUserNAI       (3),
	endUserPrivate   (4)
}

SubscriptionType ::= INTEGER (0..127)

-- PC:11816
SupplementaryServices ::= SEQUENCE 
{
 serviceType            [0] ServiceType OPTIONAL,
 serviceMode            [1] ServiceMode OPTIONAL,
 numberOfDiversions     [2] NumberOfDiversions OPTIONAL,
 associatedPartyAddress [3] AssociatedPartyAddress OPTIONAL,
 serviceID              [4] ServiceID OPTIONAL,
 changeTime             [5] ChangeTime OPTIONAL,
 numberOfParticipants   [6] NumberOfParticipants OPTIONAL,
 participantActionType  [7] ParticipantActionType OPTIONAL,
 cUGInformation         [8] CUGInformation OPTIONAL,
 ...
 }
-- PC:11816 end

TariffChangeUsage ::= ENUMERATED
{
	before            (0),
	after             (1),
	indeterminate     (2)
}

TeleServiceCode ::= ENUMERATED {
	voice             (0),
	fax               (1),
	data              (2),
	unknown           (3),
	sMS               (4),
	gPRS              (5),
	content           (6),
	videoTelephony    (7),
	videoConference   (8),
	extensionTSC1     (65526),
	extensionTSC2     (65527),
	extensionTSC3     (65528),
	extensionTSC4     (65529),
	extensionTSC5     (65530),
	extensionTSC6     (65531),
	extensionTSC7     (65532),
	extensionTSC8     (65533),
	extensionTSC9     (65534),
	extensionTSC10    (65535)
}

TimeStamp ::= OCTET STRING (SIZE(9))

TrafficCase ::= ENUMERATED {
	originatingInsideHPLMN        (0),
	forwardedInsideHPLMN          (1),
	terminatingInsideHPLMN        (2),
	originatingOutsideHPLMNCAPv1  (3),
	forwardedOutsideHPLMNCAPv1    (4),
	terminatingOutsideHPLMN       (5),
	roamingCallBackOutsideHPLMN   (6),
	originatingOutsideHPLMNCAPv2  (7),
	forwardedOutsideHPLMNCAPv2    (8),
	terminatingOutsideHPLMNCAPv2  (9),
	originatingOutsideHPLMNCAPv3  (10),
	forwardedOutsideHPLMNCAPv3    (11),
	terminatingOutsideHPLMNCAPv3  (12),
	originatingServiceCharging    (20),
	terminatingServiceCharging    (21)
}

-- PC:10210

TrunkGrpNo ::= INTEGER (0..2147483647)

TrunkInformation ::= SEQUENCE {
   inTrunkGrpNo                         [0] TrunkGrpNo        OPTIONAL,
   outTrunkGrpNo                        [1] TrunkGrpNo        OPTIONAL,
    ...
    }
-- PC:10210 end

Units::= SEQUENCE {   
 duration                       [0] ChargedDuration OPTIONAL,
 numberOfEvents                 [1] NumberOfEvents OPTIONAL,
 ... 
}

Unsigned32 ::= INTEGER (0..4294967295) 

Unsigned64 ::= INTEGER (0..18446744073709551615)

UsedServiceUnit ::= SEQUENCE {   
 tariffChangeUsage           [0] TariffChangeUsage OPTIONAL,   
 timeUnit                    [1] Unsigned32 OPTIONAL,   
 moneyUnit                   [2] MonetaryUnits OPTIONAL,   
 totalOctetsUnit             [3] Unsigned64 OPTIONAL,   
 uplinkOctetsUnit            [4] Unsigned64 OPTIONAL,
 downlinkOctetsUnit          [5] Unsigned64 OPTIONAL,   
 serviceSpecificUnit         [6] Unsigned64 OPTIONAL
}

UsedServiceUnits ::= SEQUENCE (SIZE (1..3)) OF UsedServiceUnit

UsedUnchargedDuration ::= OCTET STRING (SIZE(1..4))

UsedUnchargedEvent ::= OCTET STRING (SIZE(1..4))

UserName ::= OCTET STRING (SIZE (1..255))

UserSessionID ::= UTF8String (SIZE (1..255))

SDPCreditControlRecord ::= CHOICE
{
  creditControlRecord      [0] CreditControlRecord,
  ...
}

CreditControlRecord ::= SEQUENCE
{
  serviceIdentifier            [1]  Unsigned32,
  usedServiceUnits             [2]  UsedServiceUnits OPTIONAL,
  eventTime                    [3]  TimeStamp,
  triggerTime                  [4]  TimeStamp,
  serviceScenario              [5]  ServiceScenario,
  serviceExtension             [6]  ServiceExtension
                                 OPTIONAL,
  roamingPosition              [7]  RoamingPosition OPTIONAL,
  tariffInfo                   [8]  SEQUENCE OF
                                 SelectionTreeParameter OPTIONAL,
  cCAccountData                [9]  CCAccountData,
  chargingContextSpecific      [10] SEQUENCE OF
                                 ContextParameter OPTIONAL,
  treeDefinedFields            [11] SEQUENCE OF
                                 TreeDefinedField OPTIONAL,
  bonusAdjustment              [12] BonusAdjustment OPTIONAL,
  serviceSetupResult           [13] ServiceSetupResult OPTIONAL,
  terminationCause             [14] TerminationCause OPTIONAL,
  ratedUnits                      [15] RatedUnits OPTIONAL,
  individualPriceFactorHistory [16] SEQUENCE OF
                           IndividualPriceFactorHistory OPTIONAL,
  periodicAccountMgmtData      [17] PeriodicAccountMgmtData
                                 OPTIONAL,
  providerCreditControlRecord  [18] SEQUENCE OF
                           ProviderCreditControlRecord OPTIONAL,
  -- PC:10739
  chargingContextOutputFields  [19] SEQUENCE OF 
                           ServiceOutputField OPTIONAL,
  -- PC:10739 end
  appliedProductFees           [20] AppliedProductFees OPTIONAL,
  -- PC:11729
  daylightSavingTime           [21] DaylightSavingTime OPTIONAL,
  -- PC:11729 end
  -- PC:12961
  additionalServiceInformationFields [22] SEQUENCE OF
                      AdditionalServiceInformationField OPTIONAL,
  -- PC:12961 end
     ...
}

--------------------------------------------------------------
--
--  CREDIT CONTROL DATA TYPES
--
--------------------------------------------------------------
AccountFlags ::= IA5String (SIZE (8))

AccountGroupID ::= INTEGER (0..2147483647)

AccountSpecifiedConsumption ::= CHOICE
{
  dedicatedAccountSpecifiedConsumption [0]
                         DedicatedAccountSpecifiedConsumption,
  mainAccountSpecifiedConsumption      [1]
                         MainAccountSpecifiedConsumption,
  specifiedConsumptionNoCost           [2]
                         SpecifiedConsumptionNoCost,
  ...
}

AccountUnitType ::= ENUMERATED 
{
  time(0),
  money(1),
  totalOctets(2),
  inputOctets(3),
  outputOctets(4),
  serviceSpecificUnits(5),
  volume(6),
  ...
}

Accumulator ::= SEQUENCE
{
  accumulatorID               [0] AccumulatorID,
  accumulatorBefore           [1] Integer32 OPTIONAL,
  accumulatorChange           [2] Integer32,
  accumulatorAfter            [3] Integer32,
  accumulatorBeforeSession    [4] Integer32 OPTIONAL,
  ...
}

AccumulatorID ::= INTEGER (1..2147483647)

Accumulators ::= SEQUENCE (SIZE (1..255)) OF Accumulator

AccumulatorSpecifiedConsumptions ::= SEQUENCE OF
                          AccumulatorSpecifiedConsumption

AccumulatorSpecifiedConsumption ::= SEQUENCE
{
  accumulatorID       [0] AccumulatorID,
  accumulatorChange   [1] Integer32 OPTIONAL,
  ...
}

-- PC:12961
AdditionalServiceInformationField ::= SEQUENCE
{
  parameterType   [0] UTF8String,
  parameterName   [1] UTF8String,
  parameterValue  [2] AdditionalServiceInformationType,
  ...
}

AdditionalServiceInformationType ::= CHOICE
{
  unsigned64     [0] Unsigned64,
  decimalNumber  [1] FloatingDecimal,
  string         [2] UTF8String,
  ipAddress      [3] UTF8String,
  money          [4] MonetaryUnits,
  boolean        [5] BOOLEAN,
  ...
}
-- PC:12961 end

AddressString ::= OCTET STRING (SIZE (1..20))

AppliedProductFee ::= SEQUENCE
{
  offerID                     [0] OfferID,
  productID                   [1] ProductID,
  productFee                  [2] MonetaryUnits OPTIONAL,
  accountValueChange          [3] MonetaryUnits OPTIONAL,
  accountValueAfter           [4] MonetaryUnits OPTIONAL,
  productFeeDedicatedAccounts [5] ProductFeeDedicatedAccounts 
  OPTIONAL,
  productFeeUsageCounters     [6] ProductFeeUsageCounters OPTIONAL,
  ...
}

AppliedProductFees ::= SEQUENCE OF AppliedProductFee

BonusAdjustment ::= SEQUENCE
{
  accountValueBefore          [0]  MonetaryUnits OPTIONAL,
  accountValueAfter           [1]  MonetaryUnits OPTIONAL,
  bonusAmount                 [2]  MonetaryUnits OPTIONAL,
  accumulators                [3]  Accumulators OPTIONAL,
  dedicatedAccounts           [4]  DedicatedAccounts OPTIONAL,
  lifeCycleInformation        [5]  LifeCycleInformation OPTIONAL,
  -- PC
  aggregatedValueBefore       [6]  MonetaryUnits OPTIONAL,
  aggregatedValueAfter        [7]  MonetaryUnits OPTIONAL,
  -- end PC
  bonusOffers                 [8] SEQUENCE OF BonusOffer OPTIONAL,
  ...
}

BonusOffer ::= SEQUENCE
{
   offerID                      [0] OfferID,
   offerExpiryDateBefore        [1] Date OPTIONAL,
   offerExpiryDateAfter         [2] Date OPTIONAL,
   offerStartDateBefore         [3] Date OPTIONAL,
   offerStartDateAfter          [4] Date OPTIONAL,
   offerType                    [5] OfferType OPTIONAL,
   ...
}

CCAccountData ::= SEQUENCE
{
  servedAccount               [0]  AddressString,
  serviceClassID              [1]  ServiceClassID,
  accountGroupID              [2]  AccountGroupID,
  accountValueBefore          [3]  MonetaryUnits OPTIONAL,
  accountValueAfter           [4]  MonetaryUnits OPTIONAL,
  communityInformation        [5]  CommunityInformation OPTIONAL,
  accumulators                [6]  Accumulators OPTIONAL,
  dedicatedAccounts           [7]  DedicatedAccounts OPTIONAL,
  familyAndFriendsID          [8]  FamilyAndFriendsID OPTIONAL,
  familyAndFriendsNo          [9]  AddressString OPTIONAL,
  serviceOfferings            [10] Unsigned32,
  accumulatedCost             [11] MonetaryUnits OPTIONAL,
  accountValueUsed            [12] MonetaryUnits OPTIONAL,
  accountValueDeducted        [13] MonetaryUnits,
  -- PC
  aggregatedValueBefore       [14] MonetaryUnits OPTIONAL,
  aggregatedValueAfter        [15] MonetaryUnits OPTIONAL,
  -- end PC
  accumulatedUnits            [16] Integer64 OPTIONAL,
  accountUnitsUsed            [17] Integer64 OPTIONAL,
  accountUnitsDeducted        [18] Integer64 OPTIONAL,
  specifiedConsumptions       [19] SpecifiedConsumptions OPTIONAL,
  usedOffers                  [20] UsedOffers OPTIONAL,
  usageCounters               [21] SEQUENCE OF
                                   UsageCounter
                                   OPTIONAL,
  providersFamilyAndFriendsID [22] FamilyAndFriendsID OPTIONAL,
  -- PC:10276
  usedOffersAdditionalInfo    [23] UsedOffersAdditionalInfo OPTIONAL,
  -- PC:10276 end
  -- PC:11275
  accountHomeTimeZone         [24] TimeZone OPTIONAL,
  -- PC:11275 end
 ...

}

CommunityID ::= INTEGER (1..9999999)

CommunityIDs ::= SEQUENCE
{
  communityID1 [0] CommunityID OPTIONAL,
  communityID2 [1] CommunityID OPTIONAL,
  communityID3 [2] CommunityID OPTIONAL,
  ...
}

CommunityInformation ::= SEQUENCE
{
  selectedCommunityID         [0] CommunityID OPTIONAL,
  servedCommunityIDs          [1] CommunityIDs OPTIONAL,
  nonServedCommunityIDs       [2] CommunityIDs OPTIONAL,
  nonServedCommunityIDNA      [3] BOOLEAN OPTIONAL,
  nonServedCommunityNo        [4] AddressString OPTIONAL,
  ...
}

ContextParameter ::= SEQUENCE
{
  parameterID       [0] Integer64,
  parameterValue    [1] ContextParameterValueType
}

ContextParameterValueType ::= CHOICE
{
  boolean           [0]  BOOLEAN,
  integer32         [1]  Integer32,
  integer64         [2]  Integer64,
  unsigned32        [3]  Unsigned32,
  unsigned64        [4]  Unsigned64,
  addressString     [5]  AddressString,
  octetString       [6]  OCTET STRING,
  string            [7]  UTF8String,
  time              [8]  Time,
  partyInformation  [9]  PartyInformation,
  -- PC:09750
  group             [10] Group,
  partyInformations [11] PartyInformations,
  strings           [12] Strings,
  groups            [13] Groups,
  -- PC:09750 end
  --PC:10699  
  monetaryUnits     [14] MonetaryUnits,
  --PC:10699 end 
  ...
}

Date ::= IA5String (SIZE (8))

-- PC:11729
DaylightSavingTime ::= ENUMERATED
{
  noDaylightSavingTimeApplied (0),
  oneHourDaylightSavingTimeApplied (1),
  twoHourDaylightSavingTimeApplied (2),
  ...
}
-- PC:11729 end

DedicatedAccountSpecifiedConsumption ::= SEQUENCE
{
  dedicatedAccountID            [0] DedicatedAccountID,
  dedicatedAccountRatedUnits    [1] ServiceUnits OPTIONAL,
  dedicatedAccountDeducted      [2] MonetaryUnits,
  productID                     [3] ProductID OPTIONAL,
  ...
}

DedicatedAccount ::= SEQUENCE
{
  dedicatedAccountID          [0] DedicatedAccountID,
  dedicatedAccountValueBefore [1] MonetaryUnits OPTIONAL,
  dedicatedAccountValueAfter  [2] MonetaryUnits OPTIONAL,
  dedicatedAccountChange      [3] MonetaryUnits OPTIONAL,
  dedicatedAccountCampaignID  [4] DedicatedAccountCampaignID
                                   OPTIONAL,
  accountExpiryDateBefore     [5] Date OPTIONAL,
  accountExpiryDateAfter      [6] Date OPTIONAL,
  accountStartDateBefore      [7] Date OPTIONAL,
  accountStartDateAfter       [8] Date OPTIONAL,
  -- PC
  realMoney                   [9] BOOLEAN OPTIONAL,
  -- end PC
  offerID                     [10] OfferID OPTIONAL,
  dedicatedAccountUnitsBefore [11] Unsigned64 OPTIONAL,
  dedicatedAccountUnitsAfter  [12] Unsigned64 OPTIONAL,
  dedicatedAccountUnitsChange [13] Integer64 OPTIONAL,
  accountUnitType             [14] AccountUnitType OPTIONAL,
  subDedicatedAccounts        [15] SubDedicatedAccounts OPTIONAL,
  productID                   [16] ProductID OPTIONAL,
  -- PC:10276
  offerExpiryDate             [17] Date OPTIONAL,
  offerStartDate              [18] Date OPTIONAL,
  -- PC:10276 end
  ...
}

DedicatedAccountID ::= INTEGER (1..2147483647)

DedicatedAccountCampaignID ::= INTEGER (0..99999999)

DedicatedAccounts ::= SEQUENCE (SIZE (1..255))
                        OF DedicatedAccount

FamilyAndFriendsID ::= INTEGER (1..65535)

FloatingDecimal ::= SEQUENCE
{
   digits           [0] Integer64,
   decimals         [1] Integer32,
   ...
}

-- PC:09750
Group ::= SEQUENCE OF ContextParameter

Groups ::= SEQUENCE OF Group
-- PC:09750 end

IndividualPriceFactorHistory ::= SEQUENCE
{
  individualPriceFactor  [0] Percent,
  units                  [1] ServiceUnits,
  ...
}

Integer8 ::= INTEGER (-128..127)

Integer32 ::= INTEGER (-2147483648..2147483647)

Integer64 ::= INTEGER
                (-9223372036854775808..9223372036854775807)

LifeCycleInformation ::= SEQUENCE
{
  supervisionExpDateBefore    [0] Date OPTIONAL,
  supervisionExpDateAfter     [1] Date OPTIONAL,
  creditClearancePeriodBefore [2] Period OPTIONAL,
  creditClearancePeriodAfter  [3] Period OPTIONAL,
  servFeeExpDateBefore        [4] Date OPTIONAL,
  servFeeExpDateAfter         [5] Date OPTIONAL,
  serviceRemovalPeriodBefore  [6] Period OPTIONAL,
  serviceRemovalPeriodAfter   [7] Period OPTIONAL,
  accountFlagsBefore          [8] AccountFlags OPTIONAL,
  accountFlagsAfter           [9] AccountFlags OPTIONAL,
  ...
}

MainAccountSpecifiedConsumption ::= SEQUENCE
{
  mainAccountRatedUnits            [1] ServiceUnits OPTIONAL,
  mainAccountDeducted              [2] MonetaryUnits,
  ...
}

MonetaryUnits ::= SEQUENCE
{
  amount       [0] Integer64,
  decimals     [1] Integer32,
  currency     [2] Unsigned32
}

OfferAttributes ::= SEQUENCE OF OfferAttribute

OfferAttribute ::= SEQUENCE
{
   attributeName         [0] UTF8String,
   attributeValueString  [1] UTF8String OPTIONAL,
   ...
}

OfferID ::= INTEGER (1..2147483647)

OfferType ::= ENUMERATED
{
   account (0),
   multiUserIdentification (1),
   ...
}

PamPeriod ::= IA5String (SIZE (1..30))

PartyInformation ::= CHOICE
{
  msisdn       [0] AddressString,
  imsi         [1] AddressString,
  sipUri       [2] UTF8String,
  nai          [3] UTF8String,
  ...
}

-- PC:09750
PartyInformations ::= SEQUENCE OF PartyInformation
-- PC:09759 end

Percent ::= IA5String (SIZE (1..10))

Period ::= INTEGER (0..1023)

PeriodicAccountMgmtData ::= SEQUENCE
{
  pamServiceID     [0] Integer32,
  pamClassID       [1] Integer32,
  scheduleID       [2] Integer32,
  currentPamPeriod [3] PamPeriod,
  ...
}

PriceFactor ::= SEQUENCE
{
  priceFactor                  [0] Percent OPTIONAL,
  units                        [1] ServiceUnits OPTIONAL,
  ...
}

ProductFeeDedicatedAccount ::= SEQUENCE
{
  dedicatedAccountID         [0] DedicatedAccountID,
  dedicatedAccountChange     [1] MonetaryUnits OPTIONAL,
  dedicatedAccountValueAfter [2] MonetaryUnits OPTIONAL,
  dedicatedAccountCampaignID [3] DedicatedAccountCampaignID
  OPTIONAL,
  ...
}

ProductFeeDedicatedAccounts ::= SEQUENCE OF 
                             ProductFeeDedicatedAccount

ProductFeeUsageCounter ::= SEQUENCE
{
  usageCounterID          [0] UsageCounterID,
  usageCounterChange      [1] UsageCounterType OPTIONAL,
  usageCounterValueAfter  [2] UsageCounterType OPTIONAL,
  ...
}

ProductFeeUsageCounters ::= SEQUENCE OF 
                         ProductFeeUsageCounter

ProductID ::= INTEGER (1..2147483647)

ProviderCCAccountData ::= SEQUENCE
{
  providerAccount             [0]  AddressString,
  providerServiceClassID      [1]  ServiceClassID,
  accountGroupID              [2]  AccountGroupID,
  dedicatedAccounts           [3]  DedicatedAccounts OPTIONAL,
  familyAndFriendsID          [4]  FamilyAndFriendsID OPTIONAL,
  familyAndFriendsNo          [5]  AddressString OPTIONAL,
  accumulatedCost             [6]  MonetaryUnits OPTIONAL,
  accountValueUsed            [7]  MonetaryUnits OPTIONAL,
  accountValueDeducted        [8]  MonetaryUnits,
  accumulatedUnits            [9]  Integer64 OPTIONAL,
  accountUnitsDeducted        [11] Integer64 OPTIONAL,
  specifiedConsumptions       [12] SpecifiedConsumptions OPTIONAL,
  usageCounters               [13] SEQUENCE OF
                                   UsageCounter
                                   OPTIONAL,
  providersFamilyAndFriendsID [14] FamilyAndFriendsID OPTIONAL,
  ...
}

ProviderCreditControlRecord ::= SEQUENCE
{
   providerCCAccountData       [1] ProviderCCAccountData,
   providerRatedUnits          [2] RatedUnits OPTIONAL,
   providerPAMData             [3] PeriodicAccountMgmtData OPTIONAL,
   ...
}

Qualifier ::= INTEGER (0..4294967295)

RatedUnits ::= SEQUENCE
{
  debitUnits                 [0] RatedUnitsValues OPTIONAL,
  creditUnits                [1] RatedUnitsValues OPTIONAL,
  freeUnits                  [2] RatedUnitsValues OPTIONAL,
  ...
}

RatedUnitsValues ::= SEQUENCE
{
  ratedTimeUnits            [0] Unsigned32 OPTIONAL,
  ratedTotalOctetsUnits     [1] Unsigned64 OPTIONAL,
  ratedUplinkOctetsUnits    [2] Unsigned64 OPTIONAL,
  ratedDownlinkOctetsUnits  [3] Unsigned64 OPTIONAL,
  ratedServiceSpecificUnits [4] Unsigned64 OPTIONAL,
  ...
}

RoamingPosition ::= ENUMERATED
{
  insideHPLMN(0),
  outsideHPLMN(1),
  ...
}

SelectionTreeParameter ::= SEQUENCE
{
  selectionTreeID       [0] UTF8String,
  selectionTreeVersion  [1] UTF8String,
  selectionTreeType     [2] SelectionTreeType,
  ...
}

SelectionTreeType ::= ENUMERATED
{
  rating(0),
  bonus(1),
  selection(2),
  dedicatedAccount(3),
  communityCharging(4),
  numberNormalization(5),
  ussdTextMessage(6),
  accountManagement(7),
  preAnalysis(8),
  periodicAccountManagement(9),
  ...
}

SelectionTreeQualifiers ::= SEQUENCE OF Qualifier

ServiceClassID ::= INTEGER (0..9999)

ServiceExtension ::= ENUMERATED
{
  ussdCallback(0),
  capV1Roaming(1),
  ...
}

-- PC:10739 
ServiceOutputField ::= SEQUENCE
{
  parameterID       [0] Unsigned32,
  parameterValue    [1] ServiceOutputFieldType,
  parameterName     [2] UTF8String OPTIONAL,
  ...
}

ServiceOutputFieldType ::= CHOICE
{
  integer64   [0] Integer64,
  string      [1] UTF8String,
  octetString [2] OCTET STRING,
   ...
}
-- PC:10739 end

ServiceScenario ::= ENUMERATED
{
  mobileOriginating(0),
  mobileForwarding(1),
  mobileTerminating(2),
  ...
}

ServiceSetupResult ::= ENUMERATED
{
  successfulReleasedByService(0),
  successfulDisconnectedByCallingParty(1),
  successfulDisconnectByCalledParty(2),
  successfulTollfree(3),
  nonSuccessfulCalledPartyRouteSelectFailure(4),
  nonSuccessfulCalledPartyBusy(5),
  nonSuccessfulCalledPartyNotReachable(6),
  nonSuccessfulCalledPartyNoAnswer(7),
  nonSuccessfulCallingPartyAbandon(8),
  nonSuccessfulOtherReason(14),
-- PC:09548
  callForwardingChargingCancelled(15),
-- PC:09548 end
  ...
}

ServiceUnits ::= SEQUENCE
{
  timeUnit            [1] Unsigned32 OPTIONAL,
  moneyUnit           [2] MonetaryUnits OPTIONAL,
  totalOctetsUnit     [3] Unsigned64 OPTIONAL,
  uplinkOctetsUnit    [4] Unsigned64 OPTIONAL,
  downlinkOctetsUnit  [5] Unsigned64 OPTIONAL,
  serviceSpecificUnit [6] Unsigned64 OPTIONAL,
  ...
}

SpecifiedConsumption ::= SEQUENCE
{
  selectionTreeQualifiers         [0] SelectionTreeQualifiers,
  specifiedConsumptionAccounts    [1] SpecifiedConsumptionAccounts,
  offerID                         [2] OfferID OPTIONAL,
  individualPriceFactorAtUnit     [3]
                      IndividualPriceFactorHistory OPTIONAL,
  terminationAtUnit               [4] ServiceUnits OPTIONAL,
  eligibleOfferAtUnit             [5] ServiceUnits OPTIONAL,
  offerProviderID                 [6] AddressString OPTIONAL,
  productID                       [7] ProductID OPTIONAL,
  offerAttributes                 [8] OfferAttributes OPTIONAL,
  -- Tag 9 reserved
  priceFactorAtUnit              [10] PriceFactor OPTIONAL, 
  ...
}

SpecifiedConsumptionAccounts ::= SEQUENCE OF
                              SpecifiedConsumptionPerAccount

SpecifiedConsumptionNoCost ::= SEQUENCE
{
  providedUnits                     [1] ServiceUnits,
  ...
}

SpecifiedConsumptionPerAccount ::= SEQUENCE
{
  units                             [1] ServiceUnits,
  accountSpecifiedConsumption       [2]
                     AccountSpecifiedConsumption,
  accumulatorSpecifiedConsumptions  [3]
                     AccumulatorSpecifiedConsumptions OPTIONAL,
  usageCounterSpecifiedConsumptions [4]
                     UsageCounterSpecifiedConsumptions OPTIONAL,
  ...
}

SpecifiedConsumptions ::= SEQUENCE OF SpecifiedConsumption

-- PC:09750 
Strings ::= SEQUENCE OF UTF8String
-- PC:09750 end

SubDedicatedAccount ::= SEQUENCE
{
  dedicatedAccountID          [0] DedicatedAccountID,
  dedicatedAccountValueBefore [1] MonetaryUnits OPTIONAL,
  dedicatedAccountValueAfter  [2] MonetaryUnits OPTIONAL,
  dedicatedAccountChange      [3] MonetaryUnits OPTIONAL,
  accountExpiryDateAfter      [4] Date OPTIONAL,
  accountStartDateAfter       [5] Date OPTIONAL,
  dedicatedAccountUnitsBefore [6] Unsigned64 OPTIONAL,
  dedicatedAccountUnitsAfter  [7] Unsigned64 OPTIONAL,
  dedicatedAccountUnitsChange [8] Integer64 OPTIONAL,
 ...
}

SubDedicatedAccounts ::= SEQUENCE OF SubDedicatedAccount

TariffChangeUsage ::= ENUMERATED
{
  before(0),
  after(1),
  indeterminate(2),
  ...
}

TerminationCause ::= ENUMERATED
{
  diameterLogout(1),
  diameterServiceNotProvided(2),
  diameterBadAnswer(3),
  diameterAdministrative(4),
  diameterLinkBroken(5),
  diameterAuthExpired(6),
  diameterUserMoved(7),
  diameterSessionTimeout(8),
  ...
}

Time ::= SEQUENCE
{
  sec      [0] Integer32,
  tz       [1] Integer8
}

TimeStamp ::= IA5String (SIZE(19))

-- PC:11275
TimeZone ::= IA5String (SIZE(1..256))
-- PC:11275 end

TreeDefinedField ::= SEQUENCE
{
  parameterID       [0] UTF8String,
  parameterValue    [1] TreeDefinedFieldType
}

TreeDefinedFieldType ::= CHOICE
{
   boolean            [0] BOOLEAN,
   integer64          [2] Integer64,
   date               [6] Date,
   string             [7] UTF8String,
   floatingDecimalTDF [8] FloatingDecimal,
   amountTDF          [9] MonetaryUnits,
   ...
}

Unsigned32 ::= INTEGER (0..4294967295)

Unsigned64 ::= INTEGER (0..18446744073709551615)

UsageCounter ::= SEQUENCE 
{
   usageCounterID                 [0] UsageCounterID,
   usageCounterValueBefore        [1] UsageCounterType OPTIONAL,
   usageCounterValueAfter         [2] UsageCounterType OPTIONAL,
   usageCounterChange             [3] UsageCounterType OPTIONAL,
   productID                      [4] ProductID OPTIONAL,
   ...
}

UsageCounterID ::= INTEGER (1..2147483647)

UsageCounterSpecifiedConsumptions ::= SEQUENCE OF
                          UsageCounterSpecifiedConsumption

UsageCounterSpecifiedConsumption ::= SEQUENCE
{
  usageCounterID       [0] UsageCounterID,
  usageCounterChange   [1] UsageCounterType OPTIONAL,
  productID            [2] ProductID OPTIONAL,
  ...
}
UsageCounterType ::= CHOICE
{
   usageCounterUnit    [0] Integer64,
   usageCounterMoney   [1] MonetaryUnits,
   ...
}
UsedOffers ::= SEQUENCE OF OfferID

-- PC:10276
UsedOffersAdditionalInfo ::= SEQUENCE OF UsedOfferAdditionalInfo
--PC:10276 end

-- PC:10276
UsedOfferAdditionalInfo ::= SEQUENCE
{
   offerID                   [0] OfferID,
   offerExpiryDate           [1] Date OPTIONAL,
   offerStartDate            [2] Date OPTIONAL,
   offerType                 [3] OfferType OPTIONAL,
   offerDisabled             [4] BOOLEAN OPTIONAL,
   offerExpiryDateTime       [5] TimeStamp OPTIONAL,
   offerStartDateTime        [6] TimeStamp OPTIONAL,
   ...
}
--PC:10276 end

UsedServiceUnits ::= SEQUENCE (SIZE (1..3)) OF
                      UsedServiceUnit

UsedServiceUnit ::= SEQUENCE
{
  tariffChangeUsage           [0] TariffChangeUsage OPTIONAL,
  timeUnit                    [1] Unsigned32 OPTIONAL,
  moneyUnit                   [2] MonetaryUnits OPTIONAL,
  totalOctetsUnit             [3] Unsigned64 OPTIONAL,
  uplinkOctetsUnit            [4] Unsigned64 OPTIONAL,
  downlinkOctetsUnit          [5] Unsigned64 OPTIONAL,
  serviceSpecificUnit         [6] Unsigned64 OPTIONAL,
  ...
}

END
