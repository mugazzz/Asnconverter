-- ******************************************************************
--      File : AIROUTPUTCDR411A.asn1
--      No   : 360/19001-CAA 117 1259
--      Date : 2018-04-16
--      Rev  : A

-- Copyright (c) 2018 Telefonaktiebolaget LM Ericsson, Sweden.
-- All rights reserved.
-- The Copyright to the computer program(s) herein is the property of
-- Telefonaktiebolaget LM Ericsson, Sweden.
-- The program(s) may be used and/or copied with the written permission
-- from Telefonaktiebolaget LM Ericsson or in accordance with the terms
-- and conditions stipulated in the agreement/contract under which the
-- program(s) have been supplied.

-- DESCRIPTION:
--  This is the Mediator ASN.1 structure specification for the
--  charging data ouput.

-- REVISION HISTORY:
-- Rev          Date            Author          Action
-- A           2018-04-16       zektekt        Creation.

-- DEVIATIONS
-- The following has been changed, compared to the source document:
--<NONE>


-- SOURCE DOCUMENT: DRPL AIR Output CDR Version 4.11
-- No. : 11/190 59-FAY 302 35/1 Uen D1 
-- Rev : D1
--
-- ******************************************************************
-- ASN.1 Formal Description

 AIROUTPUTCDR411A
{
iso(1) 
member-body(2) 
bsi(826) 
disc(0)  
ericsson(1249) 
mobileDomain (0) 
charging (5)  
aIROUTPUTCDR (1) 
asn1Module (0)
}

DEFINITIONS IMPLICIT TAGS ::=
BEGIN

EXPORTS DetailOutputRecord;

-----------------------------------------------------------------
-- Detail Output Record
-----------------------------------------------------------------
 DetailOutputRecord ::= CHOICE 
 {
 -- tags [0] reserved
 -- tags [1] reserved
 -- tags [2] reserved
 -- tags [3] reserved
 adjustmentRecordV2          [4] AdjustmentRecordV2,
 offlinepromotionRecordV2    [5] OfflinePromotionRecordV2,
 refillRecordV2              [6] RefillRecordV2,
 errorRecordV2               [7] ErrorRecordV2,
 communicationIDChangeRecord [8] CommunicationIDChangeRecord,
-- PC:15605
cdrFileControlBlock          [9] CDRFileControlBlock
-- end PC:15605
}

-----------------------------------------------------------------
-- Adjustment Record V2
-----------------------------------------------------------------
AdjustmentRecordV2 ::= SEQUENCE 
{
 originNodeType              [0] NodeType,
 originHostName              [1] IDString,
 originFileID                [2] IDString OPTIONAL,
 originTransactionID         [3] TransactionID,
 originOperatorID            [4] IDString OPTIONAL,
 originTimeStamp             [5] TimeStamp,
 hostName                    [6] NodeID,
 localSequenceNumber         [7] LocalSequenceNumber,
 timeStamp                   [8] TimeStamp,
 currentServiceClass         [9] ServiceClass,
 transactionType             [10] TransactionType OPTIONAL,
 transactionCode             [11] TransactionCode OPTIONAL,
 transactionAmount           [12] MoneyAmount OPTIONAL,
 transactionCurrency         [13] Currency,
 accountNumber               [14] NumberString,
 accountCurrency             [15] Currency OPTIONAL,
 adjustmentAmount            [16] MoneyAmount OPTIONAL,
 subscriberNumber            [17] NumberString OPTIONAL,
 accountBalance              [18] MoneyAmount OPTIONAL,
 negativeBalanceBarringDate  [19] Date OPTIONAL,
 accountFlagsBefore          [20] AccountFlags,
 accountFlagsAfter           [21] AccountFlags,
 accountGroupId              [22] AccountGroupId OPTIONAL,
 externalData1               [23] ExternalDataString OPTIONAL,
 externalData2               [24] ExternalDataString OPTIONAL,
 -- PC:00260
 creditClearancePeriodBefore [25] INTEGER OPTIONAL,
 creditClearancePeriodAfter  [26] INTEGER OPTIONAL,
 serviceFeeDateBefore        [27] Date OPTIONAL,
 serviceFeeDateAfter         [28] Date OPTIONAL,
 -- end PC:00260
 serviceFeeDaysSurplus       [29] INTEGER OPTIONAL,
 dedicatedAccounts           [30] SEQUENCE (SIZE (1..255)) OF AdjustmentDedicatedAccountV2 OPTIONAL,
 cellIdentifier              [31] CellIdentifier OPTIONAL, 
 -- PC:08288
 aggregatedBalance           [32] MoneyAmount OPTIONAL,
 -- end PC:08288
 -- PC:16524
 userName 					 [33] UTF8String OPTIONAL
 -- end PC:16524
}

AdjustmentDedicatedAccountV2 ::= SEQUENCE 
{
 dedicatedAccountID      [0] DedicatedAccountID,
 campaignIdentifier      [1] CampaignIdentifier OPTIONAL,
 transactionAmount       [2] MoneyAmount OPTIONAL,
 adjustmentAmount        [3] MoneyAmount OPTIONAL,
 accountBalance          [4] MoneyAmount OPTIONAL,
 accountExpiryDateBefore [5] Date OPTIONAL,
 accountExpiryDateAfter  [6] Date OPTIONAL,
 accountStartDateBefore  [7] Date OPTIONAL,
 accountStartDateAfter   [8] Date OPTIONAL,
 -- tags [9] reserved,
 -- tags [10] reserved, 
 dedicatedAccountUnit    [11] UnitType OPTIONAL,
 transactionUnits        [12] Units OPTIONAL,
 adjustmentUnits         [13] Units OPTIONAL,
 unitBalance             [14] Units OPTIONAL,
 -- PC:08288
 realMoneyFlag           [15] BOOLEAN OPTIONAL
 -- end PC:08288
}

-- PC:15605
-----------------------------------------------------------------
-- CDRFileControlBlock Record
-----------------------------------------------------------------
CDRFileControlBlock ::= SEQUENCE 
{
   cdrFileSequenceNumber        [1] LocalSequenceNumber,
   hostName                     [2] NodeID,
   cdrFileTimeStamp             [3] TimeStamp,
   cdrFileName                  [4] FileName,
   cdrRecordCount               [5] RecordCount
}
-- end PC:15605
-----------------------------------------------------------------
-- OfflinePromotion Record V2
-----------------------------------------------------------------
OfflinePromotionRecordV2 ::= SEQUENCE 
{
 originNodeType           [0] NodeType,
 originHostName           [1] IDString,
 originFileID             [2] IDString OPTIONAL,
 originTransactionID      [3] TransactionID,
 originOperatorID         [4] IDString OPTIONAL,
 originTimeStamp          [5] TimeStamp,
 hostName                 [6] NodeID,
 localSequenceNumber      [7] LocalSequenceNumber,
 timeStamp                [8] TimeStamp,
 currentServiceClass      [9] ServiceClass,
 transactionType          [10] TransactionType OPTIONAL,
 transactionCode          [11] TransactionCode OPTIONAL,
 transactionAmount        [12] MoneyAmount,
 transactionCurrency      [13] Currency,
 accountNumber            [14] NumberString,
 accountCurrency          [15] Currency OPTIONAL,
 promotionAmountConverted [16] MoneyAmount OPTIONAL,
 promotionDivisionAmount  [17] MoneyAmount OPTIONAL,
 subscriberNumber         [18] NumberString OPTIONAL,
 accountBalance           [19] MoneyAmount OPTIONAL,
 accountFlagsBefore       [20] AccountFlags,
 accountFlagsAfter        [21] AccountFlags,
 accountGroupId           [22] AccountGroupId OPTIONAL,
 externalData1            [23] ExternalDataString OPTIONAL,
 externalData2            [24] ExternalDataString OPTIONAL,
 dedicatedAccounts        [25] SEQUENCE (SIZE (1..255)) OF OfflinePromotionDedicatedAccountV2 OPTIONAL,
 selectionTreeParameter   [26] SEQUENCE OF SelectionTreeParameter,
 treeDefinedFields        [27] SEQUENCE OF TreeDefinedField OPTIONAL,
 activationDate           [28] Date OPTIONAL,
 accountDivisionID        [29] AccountDivisionID OPTIONAL,
 communityID1             [30] INTEGER OPTIONAL,
 communityID2             [31] INTEGER OPTIONAL,
 communityID3             [32] INTEGER OPTIONAL,
 welcomeStatus            [33] BOOLEAN OPTIONAL,
 serviceOffering          [34] INTEGER OPTIONAL,
 usageAccumulator         [35] SEQUENCE (SIZE (1..255)) OF OfflinePromotionUsageAccumulator OPTIONAL,
 accountBalanceBefore     [36] MoneyAmount OPTIONAL,
 offers                   [37] SEQUENCE OF OfflinePromotionOffer OPTIONAL,
 -- PC:08288
 aggregatedBalance        [38] MoneyAmount OPTIONAL
 -- end PC:08288
}

OfflinePromotionDedicatedAccountV2 ::= SEQUENCE 
{
 dedicatedAccountID      [0] DedicatedAccountID,
 campaignIdentifier      [1] CampaignIdentifier OPTIONAL,
 promotionDivisionAmount [2] MoneyAmount OPTIONAL,
 accountBalance          [3] MoneyAmount OPTIONAL,
 accountExpiryDate       [4] Date OPTIONAL,
 accountBalanceBefore    [5] MoneyAmount OPTIONAL,
 accountExpiryDateBefore [6] Date OPTIONAL,
 accountStartDate        [7] Date OPTIONAL,
 accountStartDateBefore  [8] Date OPTIONAL,
 offerIdentifier         [9] INTEGER OPTIONAL, 
 subDedicatedAccounts    [10] SEQUENCE OF
   OfflinePromotionSubDedicatedAccount OPTIONAL,
 dedicatedAccountUnit    [11] UnitType OPTIONAL,
 promotionDivisionUnits  [12] Units OPTIONAL,
 unitBalance             [13] Units OPTIONAL,
 unitBalanceBefore       [14] Units OPTIONAL,
 -- PC:08288
 realMoneyFlag           [15] BOOLEAN OPTIONAL
 -- end PC:08288
}

OfflinePromotionSubDedicatedAccount ::= SEQUENCE 
{
 promotionDivisionAmount [1] MoneyAmount OPTIONAL,
 accountBalance          [2] MoneyAmount OPTIONAL,
 -- tags [3] reserved,
 accountExpiryDateBefore [4] Date OPTIONAL,
 accountExpiryDateAfter  [5] Date OPTIONAL,
 accountStartDateBefore  [6] Date OPTIONAL,
 accountStartDateAfter   [7] Date OPTIONAL,
 promotionDivisionUnits  [8] Units OPTIONAL,
 unitBalance             [9] Units OPTIONAL
}

OfflinePromotionUsageAccumulator ::= SEQUENCE 
{
 usageAccumulatorID    [0] INTEGER,
 usageAccumulatorValue [1] INTEGER
}

OfflinePromotionOffer ::= SEQUENCE 
{
 offerIdentifier            [0] INTEGER,
 offerExpiryDateBefore      [1] Date OPTIONAL,
 offerExpiryDateAfter       [2] Date OPTIONAL,
 offerStartDateBefore       [3] Date OPTIONAL,
 offerStartDateAfter        [4] Date OPTIONAL,
 offerType                  [5] OfferType OPTIONAL,
 offerStartDateTimeBefore   [6] TimeStamp OPTIONAL,
 offerStartDateTimeAfter    [7] TimeStamp OPTIONAL,
 offerExpiryDateTimeBefore  [8] TimeStamp OPTIONAL,
 offerExpiryDateTimeAfter   [9] TimeStamp OPTIONAL,
 offerProductIdentifier     [10] INTEGER OPTIONAL,
 attributeInformationBefore [11] SEQUENCE OF AttributeInformation OPTIONAL,
 attributeInformationAfter  [12] SEQUENCE OF AttributeInformation OPTIONAL,
 -- PC:15131 start
 offerExternalProductIdentifier [13] ProductIdString OPTIONAL,
 -- PC:15131 end
 productOfferingName        [14] ProductOfferingName OPTIONAL
 }

-----------------------------------------------------------------
-- Refill Record V2
-----------------------------------------------------------------
RefillRecordV2 ::= SEQUENCE 
{
 originNodeType                 [0] NodeType,
 originHostName                 [1] IDString,
 originFileID                   [2] IDString OPTIONAL,
 originTransactionID            [3] TransactionID,
 originOperatorID               [4] IDString OPTIONAL,
 originTimeStamp                [5] TimeStamp,
 hostName                       [6] NodeID,
 localSequenceNumber            [7] LocalSequenceNumber,
 timeStamp                      [8] TimeStamp,
 currentServiceClass            [9] ServiceClass,
 voucherBasedRefill             [10] BOOLEAN,
 transactionType                [11] TransactionType OPTIONAL,
 transactionCode                [12] TransactionCode OPTIONAL,
 transactionAmount              [13] MoneyAmount OPTIONAL,
 transactionCurrency            [14] Currency OPTIONAL,
 refillAmountConverted          [15] MoneyAmount OPTIONAL,
 refillDivisionAmount           [16] MoneyAmount OPTIONAL,
 refillType                     [17] RefillTypeV2,
 refillProfileID                [18] RefillProfileID OPTIONAL,
 segmentationID                 [19] SegmentationID OPTIONAL,
 voucherSerialNumber            [20] VoucherString OPTIONAL,
 voucherGroupID                 [21] VoucherGroupID OPTIONAL,
 accountNumber                  [22] NumberString,
 accountCurrency                [23] Currency OPTIONAL,
 subscriberNumber               [24] NumberString OPTIONAL,
 promotionAnnouncementCode      [25] PromotionAnnouncementCode OPTIONAL,
 accountInformationBeforeRefill [26] AccountInformation,
 accountInformationAfterRefill  [27] AccountInformation,
 refillPromoDivisionAmount      [28] MoneyAmount OPTIONAL,
 supervisionDaysPromoPart       [29] INTEGER OPTIONAL,
 supervisionDaysSurplus         [30] INTEGER OPTIONAL,
 serviceFeeDaysPromoPart        [31] INTEGER OPTIONAL,
 serviceFeeDaysSurplus          [32] INTEGER OPTIONAL,
 maximumServiceFeePeriod        [33] INTEGER OPTIONAL,
 maximumSupervisionPeriod       [34] INTEGER OPTIONAL,
 activationDate                 [35] Date OPTIONAL,
 welcomeStatus                  [36] BOOLEAN,
 voucherAgent                   [37] Agent OPTIONAL,
 promotionPlanAllocStartDate    [38] Date OPTIONAL,
 accountGroupId                 [39] AccountGroupId OPTIONAL,
 externalData1                  [40] ExternalDataString OPTIONAL,
 externalData2                  [41] ExternalDataString OPTIONAL,
 externalData3                  [42] ExternalDataString OPTIONAL,
 externalData4                  [43] ExternalDataString OPTIONAL,
 locationNumber                 [44] LocationNumber OPTIONAL,
 voucherActivationCode          [45] VoucherString OPTIONAL,
 accountCurrencyCleared         [46] Currency OPTIONAL,
 ignoreServiceClassHierarchy    [47] BOOLEAN OPTIONAL,
 selectionTreeParameter         [48] SEQUENCE OF SelectionTreeParameter,
 treeDefinedFields              [49] SEQUENCE OF TreeDefinedField OPTIONAL,
 accountHomeRegion              [50] RegionType OPTIONAL,
 subscriberRegion               [51] RegionType OPTIONAL,
 voucherRegion                  [52] RegionType OPTIONAL,
 promotionPlanAllocEndDate      [53] Date OPTIONAL,
 requestedRefillType            [54] RefillTypeV2 OPTIONAL,
 cellIdentifier                 [55] CellIdentifier OPTIONAL, 
 -- PC:09502
 supplierID                     [56] SupplierID OPTIONAL,
 -- end PC:09502
 pamTriggered                   [57] SEQUENCE OF PamTriggered OPTIONAL,
 -- PC:16524
  userName  					[58] UTF8String OPTIONAL
-- end PC:16524
}

AccountInformation ::= SEQUENCE 
{
 accountFlags                    [0] AccountFlags,
 accountBalance                  [1] MoneyAmount OPTIONAL,
 accumulatedRefillValue          [2] MoneyAmount OPTIONAL,
 accumulatedRefillCounter        [3] INTEGER OPTIONAL,
 accumulatedProgressionValue     [4] MoneyAmount OPTIONAL,
 accumulatedProgressionCounter   [5] INTEGER OPTIONAL,
 -- PC:00260
 creditClearancePeriod           [6] INTEGER OPTIONAL,
 -- end PC:00260
 dedicatedAccounts               [7] SEQUENCE (SIZE (1..255)) OF RefillDedicatedAccountV2 OPTIONAL,
 promotionPlan                   [8] PromotionPlanID OPTIONAL,
 permanentServiceClass           [9] ServiceClass,
 temporaryServiceClass           [10] ServiceClass OPTIONAL,
 temporaryServiceClassExpiryDate [11] Date OPTIONAL,
 refillOption                    [12] RefillOption OPTIONAL,
 -- PC:00260
 serviceFeeExpiryDate            [13] Date OPTIONAL,
 -- end PC:00260
 serviceRemovalGracePeriod       [14] INTEGER OPTIONAL,
 serviceOffering                 [15] INTEGER OPTIONAL,
 supervisionExpiryDate           [16] Date OPTIONAL,
 usageAccumulator                [17] SEQUENCE (SIZE (1..255)) OF RefillUsageAccumulator OPTIONAL,
 communityID1                    [18] INTEGER OPTIONAL,
 communityID2                    [19] INTEGER OPTIONAL,
 communityID3                    [20] INTEGER OPTIONAL,
 offers                          [21] SEQUENCE OF RefillOffer OPTIONAL,
 -- PC:08288
 aggregatedBalance               [22] MoneyAmount OPTIONAL
 -- end PC:08288
}

AttributeInformation ::= SEQUENCE 
{
   attributeName            [0] UTF8String,
   attributeValue           [1] AttributeValueType OPTIONAL
}

AttributeValueType ::= CHOICE 
{
   string [0] UTF8String
}

PamTriggered ::= SEQUENCE 
{
  pamServiceID    [0] PamServiceID,
  pamIndicator    [1] PamIndicator OPTIONAL
}


RefillUsageAccumulator ::= SEQUENCE 
{
 usageAccumulatorID        [0] INTEGER,
 usageAccumulatorValue     [1] INTEGER,
 usageAccumulatorStartDate [2] Date OPTIONAL -- PC:09649
 }

RefillDedicatedAccountV2 ::= SEQUENCE 
{
 dedicatedAccountID        [0] DedicatedAccountID,
 campaignIdentifier        [1] CampaignIdentifier OPTIONAL,
 refillDivisionAmount      [2] MoneyAmount OPTIONAL,
 refillPromoDivisionAmount [3] MoneyAmount OPTIONAL,
 accountBalance            [4] MoneyAmount OPTIONAL,
 accountExpiryDate         [5] Date OPTIONAL,
 clearedAccountValue       [6] MoneyAmount OPTIONAL,
 dedicatedAccountUnit      [7] UnitType OPTIONAL,
 accountStartDate          [8] Date OPTIONAL,
 offerIdentifier           [9] INTEGER OPTIONAL, 
 subDedicatedAccounts      [10] SEQUENCE OF RefillSubDedicatedAccount OPTIONAL,
 refillDivisionUnits       [11] Units OPTIONAL,
 refillPromoDivisionUnits  [12] Units OPTIONAL,
 unitBalance               [13] Units OPTIONAL,
 clearedUnits              [14] Units OPTIONAL,
 -- PC:08288
 realMoneyFlag             [15] BOOLEAN OPTIONAL
 -- end PC:08288
 }

RefillSubDedicatedAccount ::= SEQUENCE 
{
 refillDivisionAmount      [0] MoneyAmount OPTIONAL,
 refillPromoDivisionAmount [1] MoneyAmount OPTIONAL,
 accountBalance            [2] MoneyAmount OPTIONAL,
 -- tag [3] reserved,
 accountExpiryDate         [4] Date OPTIONAL,
 accountStartDate          [5] Date OPTIONAL,
 refillDivisionUnits       [6] Units OPTIONAL,
 refillPromoDivisionUnits  [7] Units OPTIONAL,
 unitBalance               [8] Units OPTIONAL
}

RefillOffer ::= SEQUENCE 
{
 offerIdentifier        [0] INTEGER,
 offerStartDate         [1] Date OPTIONAL, 
 offerExpiryDate        [2] Date OPTIONAL,
 offerType              [3] OfferType OPTIONAL,
 offerProductIdentifier [4] INTEGER OPTIONAL,
 offerStartDateTime     [5] TimeStamp OPTIONAL,
 offerExpiryDateTime    [6] TimeStamp OPTIONAL,
 attributeInformation   [7] SEQUENCE OF AttributeInformation OPTIONAL,
 dedicatedAccounts      [8] SEQUENCE (SIZE (1..255)) OF RefillDedicatedAccountV2 OPTIONAL,
 -- PC:15131 start
 offerExternalProductIdentifier [9] ProductIdString OPTIONAL,
 -- PC:15131 end
 productOfferingName    [10] ProductOfferingName OPTIONAL
}

-----------------------------------------------------------------
-- Error Record V2
-----------------------------------------------------------------
ErrorRecordV2 ::= SEQUENCE 
{
 originNodeType       [0] NodeType,
 originHostName       [1] IDString,
 originFileID         [2] IDString OPTIONAL,
 originTransactionID  [3] TransactionID,
 originOperatorID     [4] IDString OPTIONAL,
 originTimeStamp      [5] TimeStamp,
 hostName             [6] NodeID,
 localSequenceNumber  [7] LocalSequenceNumber,
 timeStamp            [8] TimeStamp,
 currentServiceClass  [9] ServiceClass OPTIONAL,
 operation            [10] OperationV2,
 transactionType      [11] TransactionType OPTIONAL,
 transactionCode      [12] TransactionCode OPTIONAL,
 voucherSerialNumber  [13] VoucherString OPTIONAL,
 accountNumber        [14] NumberString OPTIONAL,
 subscriberNumber     [15] NumberString,
 refillFraudCounter   [16] INTEGER OPTIONAL,
 refillUnbarTimeStamp [17] TimeStamp OPTIONAL,
 activationCode       [18] VoucherString OPTIONAL,
 errorCode            [19] ErrorCode,
 transactionAmount    [20] MoneyAmount OPTIONAL,
 transactionCurrency  [21] Currency OPTIONAL,
 locationNumber       [22] LocationNumber OPTIONAL,
 refillType           [23] RefillTypeV2 OPTIONAL,
 voucherBasedRefill   [24] BOOLEAN OPTIONAL,
 accountHomeRegion    [25] RegionType OPTIONAL,
 subscriberRegion     [26] RegionType OPTIONAL,
 voucherRegion        [27] RegionType OPTIONAL,
 requestedRefillType  [28] RefillTypeV2 OPTIONAL,
 -- PC:11945 start
 externalData1        [29] ExternalDataString OPTIONAL,
 externalData2        [30] ExternalDataString OPTIONAL,
 externalData3        [31] ExternalDataString OPTIONAL,
 externalData4        [32] ExternalDataString OPTIONAL,
 voucherGroupID       [33] VoucherGroupID OPTIONAL,
 -- PC:11945 end
 treeDefinedFields    [34] SEQUENCE OF TreeDefinedField OPTIONAL,
 -- PC:16524
 userName  	      [35] UTF8String OPTIONAL
 -- end PC:16524
}

-----------------------------------------------------------------
--CommunicationIDChange Record
-----------------------------------------------------------------
CommunicationIDChangeRecord ::= SEQUENCE 
{
 originNodeType        [0] NodeType,
 originHostName        [1] IDString,
 originFileID          [2] IDString OPTIONAL,
 originTransactionID   [3] TransactionID,
 originOperatorID      [4] IDString OPTIONAL,
 originTimeStamp       [5] TimeStamp,
 hostName              [6] NodeID,
 localSequenceNumber   [7] LocalSequenceNumber,
 timeStamp             [8] TimeStamp,
 msisdnCurrent         [9] NumberString OPTIONAL,
 msisdnNew             [10] NumberString OPTIONAL,
 imsiCurrent           [11] NumberString OPTIONAL,
 imsiNew               [12] NumberString OPTIONAL,
 naiCurrent            [13] ExtendedAddressString OPTIONAL,
 naiNew                [14] ExtendedAddressString OPTIONAL,
 sipUriCurrent         [15] ExtendedAddressString OPTIONAL,
 sipUriNew             [16] ExtendedAddressString OPTIONAL,
 privateCurrent        [17] ExtendedAddressString OPTIONAL,
 privateNew            [18] ExtendedAddressString OPTIONAL,
 cleanupDate           [19] Date OPTIONAL,
 msisdnChange          [20] BOOLEAN OPTIONAL,
 externalAddressChange [21] BOOLEAN OPTIONAL
}
-----------------------------------------------------------------
-- Parameter Types
-----------------------------------------------------------------
AccountDivisionID ::= IA5String (SIZE (1..2))

AccountFlags ::= IA5String (SIZE(8))

AccountGroupId ::= INTEGER (0..2147483647)

Agent ::= IA5String (SIZE (1..8))

CampaignIdentifier ::= INTEGER (1..99999999)

CellIdentifier ::= IA5String (SIZE (10..19))

Currency ::= IA5String (SIZE (3))

Date ::= IA5String (SIZE (8))

DedicatedAccountID ::= INTEGER (1..2147483647)

ErrorCode ::= ENUMERATED 
{
 otherError (0),
 internalSystemFault (1),
 subscriberNotFound (2),
 accountBarredFromRefill (3),
 temporaryBlocked (4),
 dedicatedAccountNotAllowed (5),
 dedicatedAccountNegative (6),
 voucherStatusUsedBySame (7),
 voucherStatusUsedByDifferent (8),
 voucherStatusUnavailable (9),
 voucherStatusExpired (10),
 voucherStatusStolenOrMissing (11),
 voucherStatusDamaged (12),
 voucherStatusPending (13),
 voucherTypeNotAccepted (14),
 voucherGroupServiceClassErr (15),
 serviceClassHierarchyErr (16),
 serviceClassChangeNotAllowed (17),
 valueVoucherNotActive (18),
 invalidActivationNumber (19),
 invalidPaymentProfile (20),
 supervisionPeriodTooLong (21),
 serviceFeePeriodTooLong (22),
 maxCreditLimitExceeded (23),
 belowMinimumBalance (24),
 accountUpdateResultUnknown (25)
}

ExtendedAddressString ::= IA5String (SIZE (1..128))

ExternalDataString ::= IA5String (SIZE (1..255))

-- PC:15605
FileName ::= IA5String (SIZE(1..255))
-- PC:15605 end

IDString ::= IA5String (SIZE (1..255))

Integer64 ::= INTEGER (-9223372036854775808..9223372036854775807)

LocalSequenceNumber ::= INTEGER (0..4294967295)

LocationNumber ::= IA5String (SIZE (1..20))

MoneyAmount ::= IA5String (SIZE (1..21))

NodeID ::= IA5String (SIZE (1..20))

NodeType ::= IA5String (SIZE (1..8))

NumberString ::= IA5String (SIZE (1..30))

OfferType ::= ENUMERATED 
{
 account                 (0),
 multiUserIdentification (1),
 timer                   (2),
 providerAccount         (3),
 sharedAccount           (4)
}

OperationV2 ::= ENUMERATED 
{
 undefined        (0),
 refill           (1),
 adjustment       (2),
 offlinePromotion (3)
}

PamIndicator ::= INTEGER (0..65535)

PamServiceID ::= INTEGER (0..99)

Percentage ::= IA5String (SIZE (1..13))

-- PC:15131 start
ProductIdString::= IA5String (SIZE (1..55))
-- PC:15131 end

ProductOfferingName ::= IA5String (SIZE (1..128))

PromotionAnnouncementCode ::= INTEGER (0..99)

PromotionPlanID ::= IA5String (SIZE (1..4))

-- PC:15605
RecordCount ::= INTEGER (0..4294967295)
-- PC:15605 end

RefillOption ::= INTEGER (1..999)

RefillProfileID ::= IA5String (SIZE (1..4))

RefillTypeV2 ::= INTEGER (0..999)

RegionType ::= INTEGER (0..999)

SegmentationID ::= IA5String (SIZE (1..4))

ServiceClass ::= INTEGER (0..9999)

SelectionTreeID ::= IA5String (SIZE (1..5))

SelectionTreeParameter ::= SEQUENCE
{
 selectionTreeID      [0] SelectionTreeID,
 selectionTreeVersion [1] UTF8String
}

SupplierID ::= IA5String (SIZE(1..8))

TimeStamp ::= IA5String (SIZE (19))

TransactionCode ::= IA5String (SIZE (1..30))

TransactionID ::= IA5String (SIZE (1..20))
 
TransactionType ::= IA5String (SIZE (1..30))

TreeDefinedField ::= SEQUENCE
{
 parameterID    [0] UTF8String,
 parameterValue [1] TreeDefinedFieldType
}

TreeDefinedFieldType ::= CHOICE
{
 boolean   [0] BOOLEAN,
 integer64 [1] Integer64,
 string    [2] UTF8String,
 -- PC:09875
 amount    [3] UTF8String      
 -- end PC:09875
}

Units ::= IA5String (SIZE (1..21))

UnitType ::= INTEGER (0..2147483647)

VoucherGroupID ::= IA5String (SIZE(1..4))

VoucherString ::= IA5String (SIZE(8..20))

END
